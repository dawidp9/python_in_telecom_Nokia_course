EUTRA-RRC-Definitions DEFINITIONS AUTOMATIC TAGS ::=
BEGIN
BCCH-BCH-Message ::= SEQUENCE {
 message BCCH-BCH-MessageType
} 
ETSI
3GPP TS 36.331 version 11.17.0 Release 11 127 ETSI TS 136 331 V11.17.0 (2017-02)
BCCH-BCH-MessageType ::= MasterInformationBlock
BCCH-DL-SCH-Message ::= SEQUENCE {
 message BCCH-DL-SCH-MessageType
}
BCCH-DL-SCH-MessageType ::= CHOICE {
 c1 CHOICE {
 systemInformation SystemInformation,
 systemInformationBlockType1 SystemInformationBlockType1
 },
 messageClassExtension SEQUENCE {}
}
MCCH-Message ::= SEQUENCE {
 message MCCH-MessageType
}
MCCH-MessageType ::= CHOICE {
 c1 CHOICE { 
ETSI
3GPP TS 36.331 version 11.17.0 Release 11 128 ETSI TS 136 331 V11.17.0 (2017-02)
 mbsfnAreaConfiguration-r9 MBSFNAreaConfiguration-r9
 },
 later CHOICE {
 c2 CHOICE{
 mbmsCountingRequest-r10 MBMSCountingRequest-r10
 },
 messageClassExtension SEQUENCE {}
 }
}
PCCH-Message ::= SEQUENCE {
 message PCCH-MessageType
}
PCCH-MessageType ::= CHOICE {
 c1 CHOICE {
 paging Paging
 },
 messageClassExtension SEQUENCE {}
}
ETSI
3GPP TS 36.331 version 11.17.0 Release 11 129 ETSI TS 136 331 V11.17.0 (2017-02)
DL-CCCH-Message ::= SEQUENCE {
 message DL-CCCH-MessageType
}
DL-CCCH-MessageType ::= CHOICE {
 c1 CHOICE {
 rrcConnectionReestablishment RRCConnectionReestablishment,
 rrcConnectionReestablishmentReject RRCConnectionReestablishmentReject,
 rrcConnectionReject RRCConnectionReject,
 rrcConnectionSetup RRCConnectionSetup
 },
 messageClassExtension SEQUENCE {}
}
DL-DCCH-Message ::= SEQUENCE {
 message DL-DCCH-MessageType
}
DL-DCCH-MessageType ::= CHOICE {
 c1 CHOICE {
 csfbParametersResponseCDMA2000 CSFBParametersResponseCDMA2000,
 dlInformationTransfer DLInformationTransfer,
 handoverFromEUTRAPreparationRequest HandoverFromEUTRAPreparationRequest,
 mobilityFromEUTRACommand MobilityFromEUTRACommand,
 rrcConnectionReconfiguration RRCConnectionReconfiguration,
 rrcConnectionRelease RRCConnectionRelease,
 securityModeCommand SecurityModeCommand,
 ueCapabilityEnquiry UECapabilityEnquiry, 
ETSI
3GPP TS 36.331 version 11.17.0 Release 11 130 ETSI TS 136 331 V11.17.0 (2017-02)
 counterCheck CounterCheck,
 ueInformationRequest-r9 UEInformationRequest-r9,
 loggedMeasurementConfiguration-r10 LoggedMeasurementConfiguration-r10,
 rnReconfiguration-r10 RNReconfiguration-r10,
 spare4 NULL,
 spare3 NULL, spare2 NULL, spare1 NULL
 },
 messageClassExtension SEQUENCE {}
}
UL-CCCH-Message ::= SEQUENCE {
 message UL-CCCH-MessageType
}
UL-CCCH-MessageType ::= CHOICE {
 c1 CHOICE {
 rrcConnectionReestablishmentRequest RRCConnectionReestablishmentRequest,
 rrcConnectionRequest RRCConnectionRequest
 },
 messageClassExtension SEQUENCE {}
}
ETSI
3GPP TS 36.331 version 11.17.0 Release 11 131 ETSI TS 136 331 V11.17.0 (2017-02)
UL-DCCH-Message ::= SEQUENCE {
 message UL-DCCH-MessageType
}
UL-DCCH-MessageType ::= CHOICE {
 c1 CHOICE {
 csfbParametersRequestCDMA2000 CSFBParametersRequestCDMA2000,
 measurementReport MeasurementReport,
 rrcConnectionReconfigurationComplete RRCConnectionReconfigurationComplete,
 rrcConnectionReestablishmentComplete RRCConnectionReestablishmentComplete,
 rrcConnectionSetupComplete RRCConnectionSetupComplete,
 securityModeComplete SecurityModeComplete,
 securityModeFailure SecurityModeFailure,
 ueCapabilityInformation UECapabilityInformation,
 ulHandoverPreparationTransfer ULHandoverPreparationTransfer,
 ulInformationTransfer ULInformationTransfer,
 counterCheckResponse CounterCheckResponse,
 ueInformationResponse-r9 UEInformationResponse-r9,
 proximityIndication-r9 ProximityIndication-r9,
 rnReconfigurationComplete-r10 RNReconfigurationComplete-r10,
 mbmsCountingResponse-r10 MBMSCountingResponse-r10,
 interFreqRSTDMeasurementIndication-r10 InterFreqRSTDMeasurementIndication-r10
 },
 messageClassExtension CHOICE {
 c2 CHOICE {
 ueAssistanceInformation-r11 UEAssistanceInformation-r11,
 inDeviceCoexIndication-r11 InDeviceCoexIndication-r11,
 mbmsInterestIndication-r11 MBMSInterestIndication-r11,
 spare13 NULL,
 spare12 NULL, spare11 NULL, spare10 NULL,
 spare9 NULL, spare8 NULL, spare7 NULL,
 spare6 NULL, spare5 NULL, spare4 NULL,
 spare3 NULL, spare2 NULL, spare1 NULL
 }, 
ETSI
3GPP TS 36.331 version 11.17.0 Release 11 132 ETSI TS 136 331 V11.17.0 (2017-02)
 messageClassExtensionFuture-r11 SEQUENCE {}
 }
}
CounterCheck ::= SEQUENCE {
 rrc-TransactionIdentifier RRC-TransactionIdentifier,
 criticalExtensions CHOICE {
 c1 CHOICE {
 counterCheck-r8 CounterCheck-r8-IEs,
 spare3 NULL, spare2 NULL, spare1 NULL
 },
 criticalExtensionsFuture SEQUENCE {}
 }
}
CounterCheck-r8-IEs ::= SEQUENCE {
 drb-CountMSB-InfoList DRB-CountMSB-InfoList,
 nonCriticalExtension CounterCheck-v8a0-IEs OPTIONAL
}
CounterCheck-v8a0-IEs ::= SEQUENCE { 
ETSI
3GPP TS 36.331 version 11.17.0 Release 11 133 ETSI TS 136 331 V11.17.0 (2017-02)
 lateNonCriticalExtension OCTET STRING OPTIONAL,
 nonCriticalExtension SEQUENCE {} OPTIONAL
}
DRB-CountMSB-InfoList ::= SEQUENCE (SIZE (1..maxDRB)) OF DRB-CountMSB-Info
DRB-CountMSB-Info ::= SEQUENCE {
drb-Identity
 DRBIdentity,

 countMSB-Uplink INTEGER(0..33554431),
 countMSB-Downlink INTEGER(0..33554431)
}
CounterCheckResponse ::= SEQUENCE {
 rrc-TransactionIdentifier RRC-TransactionIdentifier,
 criticalExtensions CHOICE {
 counterCheckResponse-r8 CounterCheckResponse-r8-IEs,
 criticalExtensionsFuture SEQUENCE {} 
ETSI
3GPP TS 36.331 version 11.17.0 Release 11 134 ETSI TS 136 331 V11.17.0 (2017-02)
 }
}
CounterCheckResponse-r8-IEs ::= SEQUENCE {
 drb-CountInfoList DRB-CountInfoList,
 nonCriticalExtension CounterCheckResponse-v8a0-IEs OPTIONAL
}
CounterCheckResponse-v8a0-IEs ::= SEQUENCE {
 lateNonCriticalExtension OCTET STRING OPTIONAL,
 nonCriticalExtension SEQUENCE {} OPTIONAL
}
DRB-CountInfoList ::= SEQUENCE (SIZE (0..maxDRB)) OF DRB-CountInfo
DRB-CountInfo ::= SEQUENCE {
drb-Identity

DRB-Identity,
count-Uplink INTEGER(0..4294967295),
count-Downlink INTEGER(0..4294967295)
}
CSFBParametersRequestCDMA2000 ::= SEQUENCE {
 criticalExtensions CHOICE {
 csfbParametersRequestCDMA2000-r8 CSFBParametersRequestCDMA2000-r8-IEs,
 criticalExtensionsFuture SEQUENCE {}
 }
}
CSFBParametersRequestCDMA2000-r8-IEs ::= SEQUENCE {
 nonCriticalExtension CSFBParametersRequestCDMA2000-v8a0-IEs OPTIONAL
}
CSFBParametersRequestCDMA2000-v8a0-IEs ::= SEQUENCE {
 lateNonCriticalExtension OCTET STRING OPTIONAL,
 nonCriticalExtension SEQUENCE {} OPTIONAL
}
ETSI
3GPP TS 36.331 version 11.17.0 Release 11 136 ETSI TS 136 331 V11.17.0 (2017-02)
CSFBParametersResponseCDMA2000 ::= SEQUENCE {
 rrc-TransactionIdentifier RRC-TransactionIdentifier,
 criticalExtensions CHOICE {
 csfbParametersResponseCDMA2000-r8 CSFBParametersResponseCDMA2000-r8-IEs,
 criticalExtensionsFuture SEQUENCE {}
 }
}
CSFBParametersResponseCDMA2000-r8-IEs ::= SEQUENCE {
 rand RAND-CDMA2000,
 mobilityParameters MobilityParametersCDMA2000,
 nonCriticalExtension CSFBParametersResponseCDMA2000-v8a0-IEs OPTIONAL
}
CSFBParametersResponseCDMA2000-v8a0-IEs ::= SEQUENCE {
 lateNonCriticalExtension OCTET STRING OPTIONAL,
 nonCriticalExtension SEQUENCE {} OPTIONAL
}
DLInformationTransfer ::= SEQUENCE {
 rrc-TransactionIdentifier RRC-TransactionIdentifier,
 criticalExtensions CHOICE {
 c1 CHOICE { 
ETSI
3GPP TS 36.331 version 11.17.0 Release 11 137 ETSI TS 136 331 V11.17.0 (2017-02)
 dlInformationTransfer-r8 DLInformationTransfer-r8-IEs,
 spare3 NULL, spare2 NULL, spare1 NULL
 },
 criticalExtensionsFuture SEQUENCE {}
 }
}
DLInformationTransfer-r8-IEs ::= SEQUENCE {
 dedicatedInfoType CHOICE {
 dedicatedInfoNAS DedicatedInfoNAS,
 dedicatedInfoCDMA2000-1XRTT DedicatedInfoCDMA2000,
 dedicatedInfoCDMA2000-HRPD DedicatedInfoCDMA2000
 },
 nonCriticalExtension DLInformationTransfer-v8a0-IEs OPTIONAL
}
DLInformationTransfer-v8a0-IEs ::= SEQUENCE {
 lateNonCriticalExtension OCTET STRING OPTIONAL,
 nonCriticalExtension SEQUENCE {} OPTIONAL
}
ETSI
3GPP TS 36.331 version 11.17.0 Release 11 138 ETSI TS 136 331 V11.17.0 (2017-02)
HandoverFromEUTRAPreparationRequest ::= SEQUENCE {
 rrc-TransactionIdentifier RRC-TransactionIdentifier,
 criticalExtensions CHOICE {
 c1 CHOICE {
 handoverFromEUTRAPreparationRequest-r8
 HandoverFromEUTRAPreparationRequest-r8-IEs,
 spare3 NULL, spare2 NULL, spare1 NULL
 },
 criticalExtensionsFuture SEQUENCE {}
 }
}
HandoverFromEUTRAPreparationRequest-r8-IEs ::= SEQUENCE {
 cdma2000-Type CDMA2000-Type,
 rand RAND-CDMA2000 OPTIONAL, -- Cond cdma2000-Type
 mobilityParameters MobilityParametersCDMA2000 OPTIONAL, -- Cond cdma2000-Type
 nonCriticalExtension HandoverFromEUTRAPreparationRequest-v890-IEs OPTIONAL
}
HandoverFromEUTRAPreparationRequest-v890-IEs ::= SEQUENCE {
 lateNonCriticalExtension OCTET STRING OPTIONAL,
 nonCriticalExtension HandoverFromEUTRAPreparationRequest-v920-IEs OPTIONAL
}
HandoverFromEUTRAPreparationRequest-v920-IEs ::= SEQUENCE {
 concurrPrepCDMA2000-HRPD-r9 BOOLEAN OPTIONAL, -- Cond cdma2000-Type
 nonCriticalExtension HandoverFromEUTRAPreparationRequest-v1020-IEs OPTIONAL
}
HandoverFromEUTRAPreparationRequest-v1020-IEs ::= SEQUENCE {
 dualRxTxRedirectIndicator-r10 ENUMERATED {true} OPTIONAL, -- Cond cdma2000-1XRTT
 redirectCarrierCDMA2000-1XRTT-r10 CarrierFreqCDMA2000 OPTIONAL, -- Cond dualRxTxRedirect
 nonCriticalExtension SEQUENCE {} OPTIONAL
} 
ETSI
3GPP TS 36.331 version 11.17.0 Release 11 139 ETSI TS 136 331 V11.17.0 (2017-02)
InDeviceCoexIndication-r11 ::= SEQUENCE {
 criticalExtensions CHOICE {
 c1 CHOICE {
 inDeviceCoexIndication-r11 InDeviceCoexIndication-r11-IEs,
 spare3 NULL, spare2 NULL, spare1 NULL
 },
 criticalExtensionsFuture SEQUENCE {}
 }
}
InDeviceCoexIndication-r11-IEs ::= SEQUENCE {
 affectedCarrierFreqList-r11 AffectedCarrierFreqList-r11 OPTIONAL,
 tdm-AssistanceInfo-r11 TDM-AssistanceInfo-r11 OPTIONAL, 
ETSI
3GPP TS 36.331 version 11.17.0 Release 11 140 ETSI TS 136 331 V11.17.0 (2017-02)
 lateNonCriticalExtension OCTET STRING OPTIONAL,
 nonCriticalExtension InDeviceCoexIndication-v11d0-IEs OPTIONAL
}
InDeviceCoexIndication-v11d0-IEs ::= SEQUENCE {
 ul-CA-AssistanceInfo-r11 SEQUENCE {
 affectedCarrierFreqCombList-r11 AffectedCarrierFreqCombList-r11 OPTIONAL,
 victimSystemType-r11 VictimSystemType-r11
 } OPTIONAL,
 nonCriticalExtension SEQUENCE {} OPTIONAL
}
AffectedCarrierFreqList-r11 ::= SEQUENCE (SIZE (1..maxFreqIDC-r11)) OF AffectedCarrierFreq-r11
AffectedCarrierFreq-r11 ::= SEQUENCE {
 carrierFreq-r11 MeasObjectId,
 interferenceDirection-r11 ENUMERATED {eutra, other, both, spare}
}
AffectedCarrierFreqCombList-r11 ::= SEQUENCE (SIZE (1..maxCombIDC-r11)) OF AffectedCarrierFreqComb-r11
AffectedCarrierFreqComb-r11 ::= SEQUENCE (SIZE (2..maxServCell-r10)) OF MeasObjectId
TDM-AssistanceInfo-r11 ::= CHOICE {
 drx-AssistanceInfo-r11 SEQUENCE {
 drx-CycleLength-r11 ENUMERATED {sf40, sf64, sf80, sf128, sf160,
 sf256, spare2, spare1},
 drx-Offset-r11 INTEGER (0..255) OPTIONAL,
 drx-ActiveTime-r11 ENUMERATED {sf20, sf30, sf40, sf60, sf80,
 sf100, spare2, spare1}
 },
 idc-SubframePatternList-r11 IDC-SubframePatternList-r11,
 ...
} 
ETSI
3GPP TS 36.331 version 11.17.0 Release 11 141 ETSI TS 136 331 V11.17.0 (2017-02)
IDC-SubframePatternList-r11 ::= SEQUENCE (SIZE (1..maxSubframePatternIDC-r11)) OF IDC-SubframePatternr11

IDC-SubframePattern-r11 ::= CHOICE {
 subframePatternFDD-r11 BIT STRING (SIZE (4)),
 subframePatternTDD-r11 CHOICE {
 subframeConfig0-r11 BIT STRING (SIZE (70)),
 subframeConfig1-5-r11 BIT STRING (SIZE (10)),
 subframeConfig6-r11 BIT STRING (SIZE (60))
 },
 ...
}
VictimSystemType-r11 ::= SEQUENCE {
 gps-r11 ENUMERATED {true} OPTIONAL,
 glonass-r11 ENUMERATED {true} OPTIONAL,
 bds-r11 ENUMERATED {true} OPTIONAL,
 galileo-r11 ENUMERATED {true} OPTIONAL,
 wlan-r11 ENUMERATED {true} OPTIONAL,
 bluetooth-r11 ENUMERATED {true} OPTIONAL
}
InterFreqRSTDMeasurementIndication-r10 ::= SEQUENCE {
 criticalExtensions CHOICE {
 c1 CHOICE {
 interFreqRSTDMeasurementIndication-r10 InterFreqRSTDMeasurementIndication-r10-IEs,
 spare3 NULL, spare2 NULL, spare1 NULL
 }, 
ETSI
3GPP TS 36.331 version 11.17.0 Release 11 143 ETSI TS 136 331 V11.17.0 (2017-02)
 criticalExtensionsFuture SEQUENCE {}
 }
}
InterFreqRSTDMeasurementIndication-r10-IEs ::= SEQUENCE {
 rstd-InterFreqIndication-r10 CHOICE {
 start SEQUENCE {
 rstd-InterFreqInfoList-r10 RSTD-InterFreqInfoList-r10
 },
 stop NULL
 },
 lateNonCriticalExtension OCTET STRING OPTIONAL,
 nonCriticalExtension SEQUENCE {} OPTIONAL
}
RSTD-InterFreqInfoList-r10 ::= SEQUENCE (SIZE(1..maxRSTD-Freq-r10)) OF RSTD-InterFreqInfo-r10
RSTD-InterFreqInfo-r10 ::= SEQUENCE {
 carrierFreq-r10 ARFCN-ValueEUTRA,
 measPRS-Offset-r10 INTEGER (0..39),
 ...,
 [[ carrierFreq-v1090 ARFCN-ValueEUTRA-v9e0 OPTIONAL
 ]]
}
LoggedMeasurementConfiguration-r10 ::= SEQUENCE {
 criticalExtensions CHOICE { 
ETSI
3GPP TS 36.331 version 11.17.0 Release 11 145 ETSI TS 136 331 V11.17.0 (2017-02)
 c1 CHOICE {
 loggedMeasurementConfiguration-r10 LoggedMeasurementConfiguration-r10-IEs,
 spare3 NULL, spare2 NULL, spare1 NULL
 },
 criticalExtensionsFuture SEQUENCE {}
 }
}
LoggedMeasurementConfiguration-r10-IEs ::= SEQUENCE {
 traceReference-r10 TraceReference-r10,
 traceRecordingSessionRef-r10 OCTET STRING (SIZE (2)),
 tce-Id-r10 OCTET STRING (SIZE (1)),
 absoluteTimeInfo-r10 AbsoluteTimeInfo-r10,
 areaConfiguration-r10 AreaConfiguration-r10 OPTIONAL, -- Need OR
 loggingDuration-r10 LoggingDuration-r10,
 loggingInterval-r10 LoggingInterval-r10,
 nonCriticalExtension LoggedMeasurementConfiguration-v1080-IEs OPTIONAL
}
LoggedMeasurementConfiguration-v1080-IEs ::= SEQUENCE {
 lateNonCriticalExtension-r10 OCTET STRING OPTIONAL,
 nonCriticalExtension LoggedMeasurementConfiguration-v1130-IEs OPTIONAL
}
LoggedMeasurementConfiguration-v1130-IEs ::= SEQUENCE {
 plmn-IdentityList-r11 PLMN-IdentityList3-r11 OPTIONAL, -- Need OR
 areaConfiguration-v1130 AreaConfiguration-v1130 OPTIONAL, -- Need OR
 nonCriticalExtension SEQUENCE {} OPTIONAL
}
MasterInformationBlock ::= SEQUENCE {
 dl-Bandwidth ENUMERATED {
 n6, n15, n25, n50, n75, n100},
 phich-Config PHICH-Config,
 systemFrameNumber BIT STRING (SIZE (8)),
 spare BIT STRING (SIZE (10))
}
MBMSCountingRequest-r10 ::= SEQUENCE {
 countingRequestList-r10 CountingRequestList-r10,
 lateNonCriticalExtension OCTET STRING OPTIONAL,
 nonCriticalExtension SEQUENCE {} OPTIONAL
}
CountingRequestList-r10 ::= SEQUENCE (SIZE (1..maxServiceCount)) OF CountingRequestInfo-r10
CountingRequestInfo-r10 ::= SEQUENCE {
 tmgi-r10 TMGI-r9,
 ...
}
ETSI
3GPP TS 36.331 version 11.17.0 Release 11 148 ETSI TS 136 331 V11.17.0 (2017-02)
MBMSCountingResponse-r10 ::= SEQUENCE {
 criticalExtensions CHOICE {
 c1 CHOICE {
 countingResponse-r10 MBMSCountingResponse-r10-IEs,
 spare3 NULL, spare2 NULL, spare1 NULL
 },
 criticalExtensionsFuture SEQUENCE {}
 }
}
MBMSCountingResponse-r10-IEs ::= SEQUENCE {
 mbsfn-AreaIndex-r10 INTEGER (0..maxMBSFN-Area-1) OPTIONAL,
 countingResponseList-r10 CountingResponseList-r10 OPTIONAL,
 lateNonCriticalExtension OCTET STRING OPTIONAL,
 nonCriticalExtension SEQUENCE {} OPTIONAL
}
CountingResponseList-r10 ::= SEQUENCE (SIZE (1..maxServiceCount)) OF CountingResponseInfo-r10
CountingResponseInfo-r10 ::= SEQUENCE {
 countingResponseService-r10 INTEGER (0..maxServiceCount-1),
 ...
}
MBMSInterestIndication-r11 ::= SEQUENCE {
 criticalExtensions CHOICE {
 c1 CHOICE {
 interestIndication-r11 MBMSInterestIndication-r11-IEs,
 spare3 NULL, spare2 NULL, spare1 NULL
 },
 criticalExtensionsFuture SEQUENCE {}
 }
}
MBMSInterestIndication-r11-IEs ::= SEQUENCE {
 mbms-FreqList-r11 CarrierFreqListMBMS-r11 OPTIONAL,
 mbms-Priority-r11 ENUMERATED {true} OPTIONAL,
 lateNonCriticalExtension OCTET STRING OPTIONAL,
 nonCriticalExtension SEQUENCE {} OPTIONAL
}
MBSFNAreaConfiguration-r9 ::= SEQUENCE {
 commonSF-Alloc-r9 CommonSF-AllocPatternList-r9,
 commonSF-AllocPeriod-r9 ENUMERATED {
 rf4, rf8, rf16, rf32, rf64, rf128, rf256},
 pmch-InfoList-r9 PMCH-InfoList-r9,
 nonCriticalExtension MBSFNAreaConfiguration-v930-IEs OPTIONAL
}
MBSFNAreaConfiguration-v930-IEs ::= SEQUENCE {
 lateNonCriticalExtension OCTET STRING OPTIONAL,
 nonCriticalExtension SEQUENCE {} OPTIONAL
}
CommonSF-AllocPatternList-r9 ::= SEQUENCE (SIZE (1..maxMBSFN-Allocations)) OF MBSFN-SubframeConfig
MeasurementReport ::= SEQUENCE {
 criticalExtensions CHOICE {
 c1 CHOICE{
 measurementReport-r8 MeasurementReport-r8-IEs,
 spare7 NULL,
 spare6 NULL, spare5 NULL, spare4 NULL,
 spare3 NULL, spare2 NULL, spare1 NULL
 },
 criticalExtensionsFuture SEQUENCE {}
 }
}
MeasurementReport-r8-IEs ::= SEQUENCE {
 measResults MeasResults,
 nonCriticalExtension MeasurementReport-v8a0-IEs OPTIONAL
}
MeasurementReport-v8a0-IEs ::= SEQUENCE {
 lateNonCriticalExtension OCTET STRING OPTIONAL,
 nonCriticalExtension SEQUENCE {} OPTIONAL
}
MobilityFromEUTRACommand ::= SEQUENCE {
 rrc-TransactionIdentifier RRC-TransactionIdentifier,
 criticalExtensions CHOICE {
 c1 CHOICE{
 mobilityFromEUTRACommand-r8 MobilityFromEUTRACommand-r8-IEs,
 mobilityFromEUTRACommand-r9 MobilityFromEUTRACommand-r9-IEs,
 spare2 NULL, spare1 NULL
 },
 criticalExtensionsFuture SEQUENCE {}
 }
}
MobilityFromEUTRACommand-r8-IEs ::= SEQUENCE {
 cs-FallbackIndicator BOOLEAN,
 purpose CHOICE{
 handover Handover,
 cellChangeOrder CellChangeOrder
 },
 nonCriticalExtension MobilityFromEUTRACommand-v8a0-IEs OPTIONAL
}
MobilityFromEUTRACommand-v8a0-IEs ::= SEQUENCE {
 lateNonCriticalExtension OCTET STRING OPTIONAL,
 nonCriticalExtension MobilityFromEUTRACommand-v8d0-IEs OPTIONAL
} 
ETSI
3GPP TS 36.331 version 11.17.0 Release 11 153 ETSI TS 136 331 V11.17.0 (2017-02)
MobilityFromEUTRACommand-v8d0-IEs ::= SEQUENCE {
 bandIndicator BandIndicatorGERAN OPTIONAL, -- Cond GERAN
 nonCriticalExtension SEQUENCE {} OPTIONAL
}
MobilityFromEUTRACommand-r9-IEs ::= SEQUENCE {
 cs-FallbackIndicator BOOLEAN,
 purpose CHOICE{
 handover Handover,
 cellChangeOrder CellChangeOrder,
 e-CSFB-r9 E-CSFB-r9,
 ...
 },
 nonCriticalExtension MobilityFromEUTRACommand-v930-IEs OPTIONAL
}
MobilityFromEUTRACommand-v930-IEs ::= SEQUENCE {
 lateNonCriticalExtension OCTET STRING OPTIONAL,
 nonCriticalExtension MobilityFromEUTRACommand-v960-IEs OPTIONAL
}
MobilityFromEUTRACommand-v960-IEs ::= SEQUENCE {
 bandIndicator BandIndicatorGERAN OPTIONAL, -- Cond GERAN
 nonCriticalExtension SEQUENCE {} OPTIONAL
}
Handover ::= SEQUENCE {
 targetRAT-Type ENUMERATED {
 utra, geran, cdma2000-1XRTT, cdma2000-HRPD,
 spare4, spare3, spare2, spare1, ...},
 targetRAT-MessageContainer OCTET STRING,
 nas-SecurityParamFromEUTRA OCTET STRING (SIZE (1)) OPTIONAL, -- Cond UTRAGERAN
 systemInformation SI-OrPSI-GERAN OPTIONAL -- Cond PSHO
} 
ETSI
3GPP TS 36.331 version 11.17.0 Release 11 154 ETSI TS 136 331 V11.17.0 (2017-02)
CellChangeOrder ::= SEQUENCE {
 t304 ENUMERATED {
 ms100, ms200, ms500, ms1000,
 ms2000, ms4000, ms8000, spare1},
 targetRAT-Type CHOICE {
 geran SEQUENCE {
 physCellId PhysCellIdGERAN,
 carrierFreq CarrierFreqGERAN,
 networkControlOrder BIT STRING (SIZE (2)) OPTIONAL, -- Need OP
 systemInformation SI-OrPSI-GERAN OPTIONAL -- Need OP
 },
 ...
 }
}
SI-OrPSI-GERAN ::= CHOICE {
 si SystemInfoListGERAN,
 psi SystemInfoListGERAN
}
E-CSFB-r9 ::= SEQUENCE {
 messageContCDMA2000-1XRTT-r9 OCTET STRING OPTIONAL, -- Need ON
 mobilityCDMA2000-HRPD-r9 ENUMERATED {
 handover, redirection
 } OPTIONAL, -- Need OP
 messageContCDMA2000-HRPD-r9 OCTET STRING OPTIONAL, -- Cond concHO
 redirectCarrierCDMA2000-HRPD-r9 CarrierFreqCDMA2000 OPTIONAL -- Cond concRedir
}
Paging ::= SEQUENCE {
 pagingRecordList PagingRecordList OPTIONAL, -- Need ON
 systemInfoModification ENUMERATED {true} OPTIONAL, -- Need ON
 etws-Indication ENUMERATED {true} OPTIONAL, -- Need ON
 nonCriticalExtension Paging-v890-IEs OPTIONAL
}
Paging-v890-IEs ::= SEQUENCE {
 lateNonCriticalExtension OCTET STRING OPTIONAL,
 nonCriticalExtension Paging-v920-IEs OPTIONAL
}
Paging-v920-IEs ::= SEQUENCE {
 cmas-Indication-r9 ENUMERATED {true} OPTIONAL, -- Need ON
 nonCriticalExtension Paging-v1130-IEs OPTIONAL
}
Paging-v1130-IEs ::= SEQUENCE { 
ETSI
3GPP TS 36.331 version 11.17.0 Release 11 157 ETSI TS 136 331 V11.17.0 (2017-02)
 eab-ParamModification-r11 ENUMERATED {true} OPTIONAL, -- Need ON
 nonCriticalExtension SEQUENCE {} OPTIONAL
}
PagingRecordList ::= SEQUENCE (SIZE (1..maxPageRec)) OF PagingRecord
PagingRecord ::= SEQUENCE {
 ue-Identity PagingUE-Identity,
 cn-Domain ENUMERATED {ps, cs},
 ...
}
PagingUE-Identity ::= CHOICE {
 s-TMSI S-TMSI,
 imsi IMSI,
 ...
}
IMSI ::= SEQUENCE (SIZE (6..21)) OF IMSI-Digit
IMSI-Digit ::= INTEGER (0..9)
ProximityIndication-r9 ::= SEQUENCE {
 criticalExtensions CHOICE {
 c1 CHOICE {
 proximityIndication-r9 ProximityIndication-r9-IEs,
 spare3 NULL, spare2 NULL, spare1 NULL
 },
 criticalExtensionsFuture SEQUENCE {}
 }
}
ProximityIndication-r9-IEs ::= SEQUENCE {
 type-r9 ENUMERATED {entering, leaving},
 carrierFreq-r9 CHOICE {
 eutra-r9 ARFCN-ValueEUTRA,
 utra-r9 ARFCN-ValueUTRA,
 ...,
 eutra2-v9e0 ARFCN-ValueEUTRA-v9e0
 },
 nonCriticalExtension ProximityIndication-v930-IEs OPTIONAL
}
ProximityIndication-v930-IEs ::= SEQUENCE {
 lateNonCriticalExtension OCTET STRING OPTIONAL,
 nonCriticalExtension SEQUENCE {} OPTIONAL
} 
ETSI
3GPP TS 36.331 version 11.17.0 Release 11 159 ETSI TS 136 331 V11.17.0 (2017-02)
RNReconfiguration-r10 ::= SEQUENCE {
 rrc-TransactionIdentifier RRC-TransactionIdentifier,
 criticalExtensions CHOICE {
 c1 CHOICE {
 rnReconfiguration-r10 RNReconfiguration-r10-IEs,
 spare3 NULL, spare2 NULL, spare1 NULL
 },
 criticalExtensionsFuture SEQUENCE {}
 }
}
RNReconfiguration-r10-IEs ::= SEQUENCE {
 rn-SystemInfo-r10 RN-SystemInfo-r10 OPTIONAL, -- Need ON
 rn-SubframeConfig-r10 RN-SubframeConfig-r10 OPTIONAL, -- Need ON
 lateNonCriticalExtension OCTET STRING OPTIONAL,
 nonCriticalExtension SEQUENCE {} OPTIONAL
} 
ETSI
3GPP TS 36.331 version 11.17.0 Release 11 160 ETSI TS 136 331 V11.17.0 (2017-02)
RN-SystemInfo-r10 ::= SEQUENCE {
 systemInformationBlockType1-r10 OCTET STRING (CONTAINING SystemInformationBlockType1)
 OPTIONAL, -- Need ON
 systemInformationBlockType2-r10 SystemInformationBlockType2 OPTIONAL, -- Need ON
 ...
}
RNReconfigurationComplete-r10 ::= SEQUENCE {
 rrc-TransactionIdentifier RRC-TransactionIdentifier,
 criticalExtensions CHOICE {
 c1 CHOICE{
 rnReconfigurationComplete-r10 RNReconfigurationComplete-r10-IEs,
 spare3 NULL, spare2 NULL, spare1 NULL
 },
 criticalExtensionsFuture SEQUENCE {}
 }
}
RNReconfigurationComplete-r10-IEs ::= SEQUENCE {
 lateNonCriticalExtension OCTET STRING OPTIONAL,
 nonCriticalExtension SEQUENCE {} OPTIONAL
} 
ETSI
3GPP TS 36.331 version 11.17.0 Release 11 161 ETSI TS 136 331 V11.17.0 (2017-02)
RRCConnectionReconfiguration ::= SEQUENCE {
 rrc-TransactionIdentifier RRC-TransactionIdentifier,
 criticalExtensions CHOICE {
 c1 CHOICE{
 rrcConnectionReconfiguration-r8 RRCConnectionReconfiguration-r8-IEs,
 spare7 NULL,
 spare6 NULL, spare5 NULL, spare4 NULL,
 spare3 NULL, spare2 NULL, spare1 NULL
 },
 criticalExtensionsFuture SEQUENCE {}
 }
}
RRCConnectionReconfiguration-r8-IEs ::= SEQUENCE {
 measConfig MeasConfig OPTIONAL, -- Need ON
 mobilityControlInfo MobilityControlInfo OPTIONAL, -- Cond HO
 dedicatedInfoNASList SEQUENCE (SIZE(1..maxDRB)) OF
 DedicatedInfoNAS OPTIONAL, -- Cond nonHO
 radioResourceConfigDedicated RadioResourceConfigDedicated OPTIONAL, -- Cond HO-toEUTRA
 securityConfigHO SecurityConfigHO OPTIONAL, -- Cond HO
 nonCriticalExtension RRCConnectionReconfiguration-v890-IEs OPTIONAL
} 
ETSI
3GPP TS 36.331 version 11.17.0 Release 11 162 ETSI TS 136 331 V11.17.0 (2017-02)
RRCConnectionReconfiguration-v890-IEs ::= SEQUENCE {
 lateNonCriticalExtension OCTET STRING (CONTAINING RRCConnectionReconfiguration-v8m0-IEs)
 OPTIONAL,
 nonCriticalExtension RRCConnectionReconfiguration-v920-IEs OPTIONAL
}
-- Late non-critical extensions:
RRCConnectionReconfiguration-v8m0-IEs ::= SEQUENCE {
 -- Following field is only for pre REL-10 late non-critical extensions
 lateNonCriticalExtension OCTET STRING OPTIONAL,
 nonCriticalExtension RRCConnectionReconfiguration-v10i0-IEs OPTIONAL
}
RRCConnectionReconfiguration-v10i0-IEs ::= SEQUENCE {
 antennaInfoDedicatedPCell-v10i0 AntennaInfoDedicated-v10i0 OPTIONAL, -- Need ON
 -- Following field is only for late non-critical extensions from REL-10
 nonCriticalExtension SEQUENCE {} OPTIONAL
}
-- Regular non-critical extensions:
RRCConnectionReconfiguration-v920-IEs ::= SEQUENCE {
 otherConfig-r9 OtherConfig-r9 OPTIONAL, -- Need ON
 fullConfig-r9 ENUMERATED {true} OPTIONAL, -- Cond HO-Reestab
 nonCriticalExtension RRCConnectionReconfiguration-v1020-IEs OPTIONAL
}
RRCConnectionReconfiguration-v1020-IEs ::= SEQUENCE {
 sCellToReleaseList-r10 SCellToReleaseList-r10 OPTIONAL, -- Need ON
 sCellToAddModList-r10 SCellToAddModList-r10 OPTIONAL, -- Need ON
 nonCriticalExtension RRCConnectionReconfiguration-v1130-IEs OPTIONAL
}
RRCConnectionReconfiguration-v1130-IEs ::= SEQUENCE {
 systemInfomationBlockType1Dedicated-r11 OCTET STRING (CONTAINING SystemInformationBlockType1)
 OPTIONAL, -- Need ON 
ETSI
3GPP TS 36.331 version 11.17.0 Release 11 163 ETSI TS 136 331 V11.17.0 (2017-02)
 nonCriticalExtension SEQUENCE {} OPTIONAL
}
SCellToAddModList-r10 ::= SEQUENCE (SIZE (1..maxSCell-r10)) OF SCellToAddMod-r10
SCellToAddMod-r10 ::= SEQUENCE {
 sCellIndex-r10 SCellIndex-r10,
 cellIdentification-r10 SEQUENCE {
 physCellId-r10 PhysCellId,
 dl-CarrierFreq-r10 ARFCN-ValueEUTRA
 } OPTIONAL, -- Cond SCellAdd
 radioResourceConfigCommonSCell-r10 RadioResourceConfigCommonSCell-r10 OPTIONAL, -- Cond
SCellAdd
 radioResourceConfigDedicatedSCell-r10 RadioResourceConfigDedicatedSCell-r10 OPTIONAL, -- Cond
SCellAdd2
 ...,
 [[ dl-CarrierFreq-v1090 ARFCN-ValueEUTRA-v9e0 OPTIONAL -- Cond EARFCN-max
 ]],
 [[ antennaInfoDedicatedSCell-v10i0 AntennaInfoDedicated-v10i0 OPTIONAL -- Need ON
 ]]
}
SCellToReleaseList-r10 ::= SEQUENCE (SIZE (1..maxSCell-r10)) OF SCellIndex-r10
SecurityConfigHO ::= SEQUENCE {
 handoverType CHOICE {
 intraLTE SEQUENCE {
 securityAlgorithmConfig SecurityAlgorithmConfig OPTIONAL, -- Cond fullConfig
 keyChangeIndicator BOOLEAN,
 nextHopChainingCount NextHopChainingCount
 },
 interRAT SEQUENCE {
 securityAlgorithmConfig SecurityAlgorithmConfig,
 nas-SecurityParamToEUTRA OCTET STRING (SIZE(6))
 }
 }, 
ETSI
3GPP TS 36.331 version 11.17.0 Release 11 164 ETSI TS 136 331 V11.17.0 (2017-02)
 ...
}
ETSI
3GPP TS 36.331 version 11.17.0 Release 11 165 ETSI TS 136 331 V11.17.0 (2017-02)
RRCConnectionReconfigurationComplete ::= SEQUENCE {
 rrc-TransactionIdentifier RRC-TransactionIdentifier,
 criticalExtensions CHOICE {
 rrcConnectionReconfigurationComplete-r8
 RRCConnectionReconfigurationComplete-r8-IEs,
 criticalExtensionsFuture SEQUENCE {}
 }
}
RRCConnectionReconfigurationComplete-r8-IEs ::= SEQUENCE {
 nonCriticalExtension RRCConnectionReconfigurationComplete-v8a0-IEs OPTIONAL
}
RRCConnectionReconfigurationComplete-v8a0-IEs ::= SEQUENCE {
 lateNonCriticalExtension OCTET STRING OPTIONAL,
 nonCriticalExtension RRCConnectionReconfigurationComplete-v1020-IEs OPTIONAL
}
RRCConnectionReconfigurationComplete-v1020-IEs ::= SEQUENCE {
 rlf-InfoAvailable-r10 ENUMERATED {true} OPTIONAL,
 logMeasAvailable-r10 ENUMERATED {true} OPTIONAL,
 nonCriticalExtension RRCConnectionReconfigurationComplete-v1130-IEs OPTIONAL
}
RRCConnectionReconfigurationComplete-v1130-IEs ::= SEQUENCE {
 connEstFailInfoAvailable-r11 ENUMERATED {true} OPTIONAL,
 nonCriticalExtension SEQUENCE {} OPTIONAL
}
RRCConnectionReestablishment ::= SEQUENCE {
 rrc-TransactionIdentifier RRC-TransactionIdentifier,
 criticalExtensions CHOICE {
 c1 CHOICE{
 rrcConnectionReestablishment-r8 RRCConnectionReestablishment-r8-IEs,
 spare7 NULL,
 spare6 NULL, spare5 NULL, spare4 NULL,
 spare3 NULL, spare2 NULL, spare1 NULL
 },
 criticalExtensionsFuture SEQUENCE {}
 }
}
RRCConnectionReestablishment-r8-IEs ::= SEQUENCE {
 radioResourceConfigDedicated RadioResourceConfigDedicated,
 nextHopChainingCount NextHopChainingCount,
 nonCriticalExtension RRCConnectionReestablishment-v8a0-IEs OPTIONAL
}
RRCConnectionReestablishment-v8a0-IEs ::= SEQUENCE {
 lateNonCriticalExtension OCTET STRING OPTIONAL,
 nonCriticalExtension SEQUENCE {} OPTIONAL
}
RRCConnectionReestablishmentComplete ::= SEQUENCE {
 rrc-TransactionIdentifier RRC-TransactionIdentifier,
 criticalExtensions CHOICE {
 rrcConnectionReestablishmentComplete-r8
 RRCConnectionReestablishmentComplete-r8-IEs,
 criticalExtensionsFuture SEQUENCE {}
 }
}
RRCConnectionReestablishmentComplete-r8-IEs ::= SEQUENCE {
 nonCriticalExtension RRCConnectionReestablishmentComplete-v920-IEs OPTIONAL
}
RRCConnectionReestablishmentComplete-v920-IEs ::= SEQUENCE {
 rlf-InfoAvailable-r9 ENUMERATED {true} OPTIONAL,
 nonCriticalExtension RRCConnectionReestablishmentComplete-v8a0-IEs OPTIONAL
}
RRCConnectionReestablishmentComplete-v8a0-IEs ::= SEQUENCE {
 lateNonCriticalExtension OCTET STRING OPTIONAL,
 nonCriticalExtension RRCConnectionReestablishmentComplete-v1020-IEs OPTIONAL
}
RRCConnectionReestablishmentComplete-v1020-IEs ::= SEQUENCE {
 logMeasAvailable-r10 ENUMERATED {true} OPTIONAL, 
ETSI
3GPP TS 36.331 version 11.17.0 Release 11 168 ETSI TS 136 331 V11.17.0 (2017-02)
 nonCriticalExtension RRCConnectionReestablishmentComplete-v1130-IEs OPTIONAL
}
RRCConnectionReestablishmentComplete-v1130-IEs ::= SEQUENCE {
 connEstFailInfoAvailable-r11 ENUMERATED {true} OPTIONAL,
 nonCriticalExtension SEQUENCE {} OPTIONAL
}
RRCConnectionReestablishmentReject ::= SEQUENCE {
 criticalExtensions CHOICE {
 rrcConnectionReestablishmentReject-r8
 RRCConnectionReestablishmentReject-r8-IEs,
 criticalExtensionsFuture SEQUENCE {}
 }
}
RRCConnectionReestablishmentReject-r8-IEs ::= SEQUENCE {
 nonCriticalExtension RRCConnectionReestablishmentReject-v8a0-IEs OPTIONAL
} 
ETSI
3GPP TS 36.331 version 11.17.0 Release 11 169 ETSI TS 136 331 V11.17.0 (2017-02)
RRCConnectionReestablishmentReject-v8a0-IEs ::= SEQUENCE {
 lateNonCriticalExtension OCTET STRING OPTIONAL,
 nonCriticalExtension SEQUENCE {} OPTIONAL
}
RRCConnectionReestablishmentRequest ::= SEQUENCE {
 criticalExtensions CHOICE {
 rrcConnectionReestablishmentRequest-r8
 RRCConnectionReestablishmentRequest-r8-IEs,
 criticalExtensionsFuture SEQUENCE {}
 }
}
RRCConnectionReestablishmentRequest-r8-IEs ::= SEQUENCE {
 ue-Identity ReestabUE-Identity,
 reestablishmentCause ReestablishmentCause,
 spare BIT STRING (SIZE (2))
}
ReestabUE-Identity ::= SEQUENCE {
 c-RNTI C-RNTI,
 physCellId PhysCellId,
 shortMAC-I ShortMAC-I 
ETSI
3GPP TS 36.331 version 11.17.0 Release 11 170 ETSI TS 136 331 V11.17.0 (2017-02)
}
ReestablishmentCause ::= ENUMERATED {
 reconfigurationFailure, handoverFailure,
 otherFailure, spare1}
RRCConnectionReject ::= SEQUENCE {
 criticalExtensions CHOICE {
 c1 CHOICE {
 rrcConnectionReject-r8 RRCConnectionReject-r8-IEs,
 spare3 NULL, spare2 NULL, spare1 NULL
 },
 criticalExtensionsFuture SEQUENCE {}
 }
}
RRCConnectionReject-r8-IEs ::= SEQUENCE {
 waitTime INTEGER (1..16),
 nonCriticalExtension RRCConnectionReject-v8a0-IEs OPTIONAL 
ETSI
3GPP TS 36.331 version 11.17.0 Release 11 171 ETSI TS 136 331 V11.17.0 (2017-02)
}
RRCConnectionReject-v8a0-IEs ::= SEQUENCE {
 lateNonCriticalExtension OCTET STRING OPTIONAL,
 nonCriticalExtension RRCConnectionReject-v1020-IEs OPTIONAL
}
RRCConnectionReject-v1020-IEs ::= SEQUENCE {
 extendedWaitTime-r10 INTEGER (1..1800) OPTIONAL, -- Need ON
 nonCriticalExtension RRCConnectionReject-v1130-IEs OPTIONAL
}
RRCConnectionReject-v1130-IEs ::= SEQUENCE {
 deprioritisationReq-r11 SEQUENCE {
 deprioritisationType-r11 ENUMERATED {frequency, e-utra},
 deprioritisationTimer-r11 ENUMERATED {min5, min10, min15, min30}
 } OPTIONAL, -- Need ON
 nonCriticalExtension SEQUENCE {} OPTIONAL
}
RRCConnectionRelease ::= SEQUENCE {
 rrc-TransactionIdentifier RRC-TransactionIdentifier,
 criticalExtensions CHOICE {
 c1 CHOICE {
 rrcConnectionRelease-r8 RRCConnectionRelease-r8-IEs,
 spare3 NULL, spare2 NULL, spare1 NULL
 },
 criticalExtensionsFuture SEQUENCE {}
 }
}
RRCConnectionRelease-r8-IEs ::= SEQUENCE {
 releaseCause ReleaseCause,
 redirectedCarrierInfo RedirectedCarrierInfo OPTIONAL, -- Need ON
 idleModeMobilityControlInfo IdleModeMobilityControlInfo OPTIONAL, -- Need OP
 nonCriticalExtension RRCConnectionRelease-v890-IEs OPTIONAL
}
RRCConnectionRelease-v890-IEs ::= SEQUENCE {
 lateNonCriticalExtension OCTET STRING (CONTAINING RRCConnectionRelease-v9e0-IEs)
 OPTIONAL,
 nonCriticalExtension RRCConnectionRelease-v920-IEs OPTIONAL
}
-- Late non critical extensions
RRCConnectionRelease-v9e0-IEs ::= SEQUENCE {
 redirectedCarrierInfo-v9e0 RedirectedCarrierInfo-v9e0 OPTIONAL, -- Cond NoRedirect-r8
 idleModeMobilityControlInfo-v9e0 IdleModeMobilityControlInfo-v9e0 OPTIONAL, -- Cond
IdleInfoEUTRA 
ETSI
3GPP TS 36.331 version 11.17.0 Release 11 173 ETSI TS 136 331 V11.17.0 (2017-02)
 nonCriticalExtension SEQUENCE {} OPTIONAL
}
-- Regular non critical extensions
RRCConnectionRelease-v920-IEs ::= SEQUENCE {
 cellInfoList-r9 CHOICE {
 geran-r9 CellInfoListGERAN-r9,
 utra-FDD-r9 CellInfoListUTRA-FDD-r9,
 utra-TDD-r9 CellInfoListUTRA-TDD-r9,
 ...,
 utra-TDD-r10 CellInfoListUTRA-TDD-r10
 } OPTIONAL, -- Cond Redirection
 nonCriticalExtension RRCConnectionRelease-v1020-IEs OPTIONAL
}
RRCConnectionRelease-v1020-IEs ::= SEQUENCE {
 extendedWaitTime-r10 INTEGER (1..1800) OPTIONAL, -- Need ON
 nonCriticalExtension SEQUENCE {} OPTIONAL
}
ReleaseCause ::= ENUMERATED {loadBalancingTAUrequired,
 other, cs-FallbackHighPriority-v1020, spare1}
RedirectedCarrierInfo ::= CHOICE {
 eutra ARFCN-ValueEUTRA,
 geran CarrierFreqsGERAN,
 utra-FDD ARFCN-ValueUTRA,
 utra-TDD ARFCN-ValueUTRA,
 cdma2000-HRPD CarrierFreqCDMA2000,
 cdma2000-1xRTT CarrierFreqCDMA2000,
 ...,
utra-TDD-r10 CarrierFreqListUTRA-TDD-r10
}
RedirectedCarrierInfo-v9e0 ::= SEQUENCE { 
ETSI
3GPP TS 36.331 version 11.17.0 Release 11 174 ETSI TS 136 331 V11.17.0 (2017-02)
 eutra-v9e0 ARFCN-ValueEUTRA-v9e0
}
CarrierFreqListUTRA-TDD-r10 ::= SEQUENCE (SIZE (1..maxFreqUTRA-TDD-r10)) OF ARFCNValueUTRA

IdleModeMobilityControlInfo ::= SEQUENCE {
 freqPriorityListEUTRA FreqPriorityListEUTRA OPTIONAL, -- Need ON
 freqPriorityListGERAN FreqsPriorityListGERAN OPTIONAL, -- Need ON
 freqPriorityListUTRA-FDD FreqPriorityListUTRA-FDD OPTIONAL, -- Need ON
 freqPriorityListUTRA-TDD FreqPriorityListUTRA-TDD OPTIONAL, -- Need ON
 bandClassPriorityListHRPD BandClassPriorityListHRPD OPTIONAL, -- Need ON
 bandClassPriorityList1XRTT BandClassPriorityList1XRTT OPTIONAL, -- Need ON
 t320 ENUMERATED {
 min5, min10, min20, min30, min60, min120, min180,
 spare1} OPTIONAL, -- Need OR
 ...
}
IdleModeMobilityControlInfo-v9e0 ::= SEQUENCE {
 freqPriorityListEUTRA-v9e0 SEQUENCE (SIZE (1..maxFreq)) OF FreqPriorityEUTRA-v9e0
}
FreqPriorityListEUTRA ::= SEQUENCE (SIZE (1..maxFreq)) OF FreqPriorityEUTRA
FreqPriorityEUTRA ::= SEQUENCE {
 carrierFreq ARFCN-ValueEUTRA,
 cellReselectionPriority CellReselectionPriority
}
FreqPriorityEUTRA-v9e0 ::= SEQUENCE {
 carrierFreq-v9e0 ARFCN-ValueEUTRA-v9e0 OPTIONAL -- Cond EARFCN-max
}
FreqsPriorityListGERAN ::= SEQUENCE (SIZE (1..maxGNFG)) OF FreqsPriorityGERAN 
ETSI
3GPP TS 36.331 version 11.17.0 Release 11 175 ETSI TS 136 331 V11.17.0 (2017-02)
FreqsPriorityGERAN ::= SEQUENCE {
 carrierFreqs CarrierFreqsGERAN,
 cellReselectionPriority CellReselectionPriority
}
FreqPriorityListUTRA-FDD ::= SEQUENCE (SIZE (1..maxUTRA-FDD-Carrier)) OF FreqPriorityUTRA-FDD
FreqPriorityUTRA-FDD ::= SEQUENCE {
 carrierFreq ARFCN-ValueUTRA,
 cellReselectionPriority CellReselectionPriority
}
FreqPriorityListUTRA-TDD ::= SEQUENCE (SIZE (1..maxUTRA-TDD-Carrier)) OF FreqPriorityUTRA-TDD
FreqPriorityUTRA-TDD ::= SEQUENCE {
 carrierFreq ARFCN-ValueUTRA,
 cellReselectionPriority CellReselectionPriority
}
BandClassPriorityListHRPD ::= SEQUENCE (SIZE (1..maxCDMA-BandClass)) OF BandClassPriorityHRPD
BandClassPriorityHRPD ::= SEQUENCE {
 bandClass BandclassCDMA2000,
 cellReselectionPriority CellReselectionPriority
}
BandClassPriorityList1XRTT ::= SEQUENCE (SIZE (1..maxCDMA-BandClass)) OF BandClassPriority1XRTT
BandClassPriority1XRTT ::= SEQUENCE {
 bandClass BandclassCDMA2000,
 cellReselectionPriority CellReselectionPriority
}
CellInfoListGERAN-r9 ::= SEQUENCE (SIZE (1..maxCellInfoGERAN-r9)) OF CellInfoGERAN-r9 
ETSI
3GPP TS 36.331 version 11.17.0 Release 11 176 ETSI TS 136 331 V11.17.0 (2017-02)
CellInfoGERAN-r9 ::= SEQUENCE {
 physCellId-r9 PhysCellIdGERAN,
 carrierFreq-r9 CarrierFreqGERAN,
 systemInformation-r9 SystemInfoListGERAN
}
CellInfoListUTRA-FDD-r9 ::= SEQUENCE (SIZE (1..maxCellInfoUTRA-r9)) OF CellInfoUTRA-FDD-r9
CellInfoUTRA-FDD-r9 ::= SEQUENCE {
 physCellId-r9 PhysCellIdUTRA-FDD,
 utra-BCCH-Container-r9 OCTET STRING
}
CellInfoListUTRA-TDD-r9 ::= SEQUENCE (SIZE (1..maxCellInfoUTRA-r9)) OF CellInfoUTRA-TDD-r9
CellInfoUTRA-TDD-r9 ::= SEQUENCE {
 physCellId-r9 PhysCellIdUTRA-TDD,
 utra-BCCH-Container-r9 OCTET STRING
}
CellInfoListUTRA-TDD-r10 ::= SEQUENCE (SIZE (1..maxCellInfoUTRA-r9)) OF CellInfoUTRA-TDD-r10
CellInfoUTRA-TDD-r10 ::= SEQUENCE {
 physCellId-r10 PhysCellIdUTRA-TDD,
 carrierFreq-r10 ARFCN-ValueUTRA,
 utra-BCCH-Container-r10 OCTET STRING
}
RRCConnectionRequest ::= SEQUENCE {
 criticalExtensions CHOICE {
 rrcConnectionRequest-r8 RRCConnectionRequest-r8-IEs,
 criticalExtensionsFuture SEQUENCE {}
 }
}
RRCConnectionRequest-r8-IEs ::= SEQUENCE {
 ue-Identity InitialUE-Identity,
 establishmentCause EstablishmentCause,
 spare BIT STRING (SIZE (1))
}
InitialUE-Identity ::= CHOICE {
 s-TMSI S-TMSI,
 randomValue BIT STRING (SIZE (40))
}
EstablishmentCause ::= ENUMERATED {
 emergency, highPriorityAccess, mt-Access, mo-Signalling,
 mo-Data, delayTolerantAccess-v1020, spare2, spare1}
RRCConnectionSetup ::= SEQUENCE {
 rrc-TransactionIdentifier RRC-TransactionIdentifier,
 criticalExtensions CHOICE {
 c1 CHOICE {
 rrcConnectionSetup-r8 RRCConnectionSetup-r8-IEs,
 spare7 NULL,
 spare6 NULL, spare5 NULL, spare4 NULL,
 spare3 NULL, spare2 NULL, spare1 NULL
 },
 criticalExtensionsFuture SEQUENCE {}
 }
}
RRCConnectionSetup-r8-IEs ::= SEQUENCE {
 radioResourceConfigDedicated RadioResourceConfigDedicated,
 nonCriticalExtension RRCConnectionSetup-v8a0-IEs OPTIONAL
}
RRCConnectionSetup-v8a0-IEs ::= SEQUENCE {
 lateNonCriticalExtension OCTET STRING OPTIONAL, 
ETSI
3GPP TS 36.331 version 11.17.0 Release 11 180 ETSI TS 136 331 V11.17.0 (2017-02)
 nonCriticalExtension SEQUENCE {} OPTIONAL
}
RRCConnectionSetupComplete ::= SEQUENCE {
 rrc-TransactionIdentifier RRC-TransactionIdentifier,
 criticalExtensions CHOICE {
 c1 CHOICE{
 rrcConnectionSetupComplete-r8 RRCConnectionSetupComplete-r8-IEs,
 spare3 NULL, spare2 NULL, spare1 NULL
 },
 criticalExtensionsFuture SEQUENCE {}
 }
}
RRCConnectionSetupComplete-r8-IEs ::= SEQUENCE {
 selectedPLMN-Identity INTEGER (1..maxPLMN-r11),
 registeredMME RegisteredMME OPTIONAL,
 dedicatedInfoNAS DedicatedInfoNAS,
 nonCriticalExtension RRCConnectionSetupComplete-v8a0-IEs OPTIONAL
}
RRCConnectionSetupComplete-v8a0-IEs ::= SEQUENCE {
 lateNonCriticalExtension OCTET STRING OPTIONAL, 
ETSI
3GPP TS 36.331 version 11.17.0 Release 11 181 ETSI TS 136 331 V11.17.0 (2017-02)
 nonCriticalExtension RRCConnectionSetupComplete-v1020-IEs OPTIONAL
}
RRCConnectionSetupComplete-v1020-IEs ::= SEQUENCE {
 gummei-Type-r10 ENUMERATED {native, mapped} OPTIONAL,
 rlf-InfoAvailable-r10 ENUMERATED {true} OPTIONAL,
 logMeasAvailable-r10 ENUMERATED {true} OPTIONAL,
 rn-SubframeConfigReq-r10 ENUMERATED {required, notRequired} OPTIONAL,
 nonCriticalExtension RRCConnectionSetupComplete-v1130-IEs OPTIONAL
}
RRCConnectionSetupComplete-v1130-IEs ::= SEQUENCE {
 connEstFailInfoAvailable-r11 ENUMERATED {true} OPTIONAL,
 nonCriticalExtension SEQUENCE {} OPTIONAL
}
RegisteredMME ::= SEQUENCE {
 plmn-Identity PLMN-Identity OPTIONAL,
 mmegi BIT STRING (SIZE (16)),
 mmec MMEC
}
SecurityModeCommand ::= SEQUENCE {
 rrc-TransactionIdentifier RRC-TransactionIdentifier,
 criticalExtensions CHOICE {
 c1 CHOICE{
 securityModeCommand-r8 SecurityModeCommand-r8-IEs,
 spare3 NULL, spare2 NULL, spare1 NULL
 },
 criticalExtensionsFuture SEQUENCE {}
 }
}
SecurityModeCommand-r8-IEs ::= SEQUENCE {
 securityConfigSMC SecurityConfigSMC,
 nonCriticalExtension SecurityModeCommand-v8a0-IEs OPTIONAL
}
SecurityModeCommand-v8a0-IEs ::= SEQUENCE {
 lateNonCriticalExtension OCTET STRING OPTIONAL,
 nonCriticalExtension SEQUENCE {} OPTIONAL
}
SecurityConfigSMC ::= SEQUENCE {
 securityAlgorithmConfig SecurityAlgorithmConfig,
 ...
}
SecurityModeComplete ::= SEQUENCE {
 rrc-TransactionIdentifier RRC-TransactionIdentifier,
 criticalExtensions CHOICE {
 securityModeComplete-r8 SecurityModeComplete-r8-IEs,
 criticalExtensionsFuture SEQUENCE {}
 }
}
SecurityModeComplete-r8-IEs ::= SEQUENCE {
 nonCriticalExtension SecurityModeComplete-v8a0-IEs OPTIONAL
}
SecurityModeComplete-v8a0-IEs ::= SEQUENCE {
 lateNonCriticalExtension OCTET STRING OPTIONAL,
 nonCriticalExtension SEQUENCE {} OPTIONAL
}
SecurityModeFailure ::= SEQUENCE {
 rrc-TransactionIdentifier RRC-TransactionIdentifier,
 criticalExtensions CHOICE {
 securityModeFailure-r8 SecurityModeFailure-r8-IEs,
 criticalExtensionsFuture SEQUENCE {}
 }
}
SecurityModeFailure-r8-IEs ::= SEQUENCE {
 nonCriticalExtension SecurityModeFailure-v8a0-IEs OPTIONAL
}
SecurityModeFailure-v8a0-IEs ::= SEQUENCE {
 lateNonCriticalExtension OCTET STRING OPTIONAL,
 nonCriticalExtension SEQUENCE {} OPTIONAL
}
ETSI
3GPP TS 36.331 version 11.17.0 Release 11 185 ETSI TS 136 331 V11.17.0 (2017-02)
SystemInformation ::= SEQUENCE {
 criticalExtensions CHOICE {
 systemInformation-r8 SystemInformation-r8-IEs,
 criticalExtensionsFuture SEQUENCE {}
 }
}
SystemInformation-r8-IEs ::= SEQUENCE {
 sib-TypeAndInfo SEQUENCE (SIZE (1..maxSIB)) OF CHOICE {
 sib2 SystemInformationBlockType2,
 sib3 SystemInformationBlockType3,
 sib4 SystemInformationBlockType4,
 sib5 SystemInformationBlockType5,
 sib6 SystemInformationBlockType6,
 sib7 SystemInformationBlockType7,
 sib8 SystemInformationBlockType8,
 sib9 SystemInformationBlockType9,
 sib10 SystemInformationBlockType10,
 sib11 SystemInformationBlockType11,
 ...,
 sib12-v920 SystemInformationBlockType12-r9,
 sib13-v920 SystemInformationBlockType13-r9,
 sib14-v1130 SystemInformationBlockType14-r11,
 sib15-v1130 SystemInformationBlockType15-r11,
 sib16-v1130 SystemInformationBlockType16-r11
 },
 nonCriticalExtension SystemInformation-v8a0-IEs OPTIONAL
}
SystemInformation-v8a0-IEs ::= SEQUENCE {
 lateNonCriticalExtension OCTET STRING OPTIONAL,
 nonCriticalExtension SEQUENCE {} OPTIONAL
}
SystemInformationBlockType1 ::= SEQUENCE {
 cellAccessRelatedInfo SEQUENCE {
 plmn-IdentityList PLMN-IdentityList,
 trackingAreaCode TrackingAreaCode,
 cellIdentity CellIdentity,
 cellBarred ENUMERATED {barred, notBarred},
 intraFreqReselection ENUMERATED {allowed, notAllowed},
 csg-Indication BOOLEAN,
 csg-Identity CSG-Identity OPTIONAL -- Need OR
 },
 cellSelectionInfo SEQUENCE {
 q-RxLevMin Q-RxLevMin,
 q-RxLevMinOffset INTEGER (1..8) OPTIONAL -- Need OP
 },
 p-Max P-Max OPTIONAL, -- Need OP
 freqBandIndicator FreqBandIndicator,
 schedulingInfoList SchedulingInfoList,
 tdd-Config TDD-Config OPTIONAL, -- Cond TDD
 si-WindowLength ENUMERATED {
 ms1, ms2, ms5, ms10, ms15, ms20,
 ms40},
 systemInfoValueTag INTEGER (0..31),
 nonCriticalExtension SystemInformationBlockType1-v890-IEs OPTIONAL
} 
ETSI
3GPP TS 36.331 version 11.17.0 Release 11 187 ETSI TS 136 331 V11.17.0 (2017-02)
SystemInformationBlockType1-v890-IEs::= SEQUENCE {
 lateNonCriticalExtension OCTET STRING (CONTAINING SystemInformationBlockType1-v8h0-IEs)
 OPTIONAL,
 nonCriticalExtension SystemInformationBlockType1-v920-IEs OPTIONAL
}
-- Late non critical extensions
SystemInformationBlockType1-v8h0-IEs ::= SEQUENCE {
 multiBandInfoList MultiBandInfoList OPTIONAL, -- Need OR
 nonCriticalExtension SystemInformationBlockType1-v9e0-IEs OPTIONAL
}
SystemInformationBlockType1-v9e0-IEs ::= SEQUENCE {
 freqBandIndicator-v9e0 FreqBandIndicator-v9e0 OPTIONAL, -- Cond FBI-max
 multiBandInfoList-v9e0 MultiBandInfoList-v9e0 OPTIONAL, -- Cond mFBI-max
 nonCriticalExtension SystemInformationBlockType1-v10j0-IEs OPTIONAL
}
SystemInformationBlockType1-v10j0-IEs ::= SEQUENCE {
 freqBandInfo-r10 NS-PmaxList-r10 OPTIONAL, -- Need OR
 multiBandInfoList-v10j0 MultiBandInfoList-v10j0 OPTIONAL, -- Need OR
 nonCriticalExtension SEQUENCE {} OPTIONAL
}
-- Regular non critical extensions
SystemInformationBlockType1-v920-IEs ::= SEQUENCE {
 ims-EmergencySupport-r9 ENUMERATED {true} OPTIONAL, -- Need OR
 cellSelectionInfo-v920 CellSelectionInfo-v920 OPTIONAL, -- Cond RSRQ
 nonCriticalExtension SystemInformationBlockType1-v1130-IEs OPTIONAL
}
SystemInformationBlockType1-v1130-IEs ::= SEQUENCE {
 tdd-Config-v1130 TDD-Config-v1130 OPTIONAL, -- Cond TDD-OR
 cellSelectionInfo-v1130 CellSelectionInfo-v1130 OPTIONAL, -- Cond WB-RSRQ 
ETSI
3GPP TS 36.331 version 11.17.0 Release 11 188 ETSI TS 136 331 V11.17.0 (2017-02)
 nonCriticalExtension SEQUENCE {} OPTIONAL
}
PLMN-IdentityList ::= SEQUENCE (SIZE (1..maxPLMN-r11)) OF PLMN-IdentityInfo
PLMN-IdentityInfo ::= SEQUENCE {
 plmn-Identity PLMN-Identity,
 cellReservedForOperatorUse ENUMERATED {reserved, notReserved}
}
SchedulingInfoList ::= SEQUENCE (SIZE (1..maxSI-Message)) OF SchedulingInfo
SchedulingInfo ::= SEQUENCE {
 si-Periodicity ENUMERATED {
 rf8, rf16, rf32, rf64, rf128, rf256, rf512},
 sib-MappingInfo SIB-MappingInfo
}
SIB-MappingInfo ::= SEQUENCE (SIZE (0..maxSIB-1)) OF SIB-Type
SIB-Type ::= ENUMERATED {
 sibType3, sibType4, sibType5, sibType6,
 sibType7, sibType8, sibType9, sibType10,
 sibType11, sibType12-v920, sibType13-v920,
 sibType14-v1130, sibType15-v1130,
 sibType16-v1130, spare2, spare1, ...}
CellSelectionInfo-v920 ::= SEQUENCE {
 q-QualMin-r9 Q-QualMin-r9,
 q-QualMinOffset-r9 INTEGER (1..8) OPTIONAL -- Need OP
}
CellSelectionInfo-v1130 ::= SEQUENCE {
 q-QualMinWB-r11 Q-QualMin-r9
} 
ETSI
3GPP TS 36.331 version 11.17.0 Release 11 189 ETSI TS 136 331 V11.17.0 (2017-02)
UEAssistanceInformation-r11 ::= SEQUENCE {
 criticalExtensions CHOICE {
 c1 CHOICE {
 ueAssistanceInformation-r11 UEAssistanceInformation-r11-IEs,
 spare3 NULL, spare2 NULL, spare1 NULL
 },
 criticalExtensionsFuture SEQUENCE {}
 }
}
UEAssistanceInformation-r11-IEs ::= SEQUENCE {
 powerPrefIndication-r11 ENUMERATED {normal, lowPowerConsumption} OPTIONAL,
 lateNonCriticalExtension OCTET STRING OPTIONAL,
 nonCriticalExtension SEQUENCE {} OPTIONAL
} 
ETSI
3GPP TS 36.331 version 11.17.0 Release 11 192 ETSI TS 136 331 V11.17.0 (2017-02)
UECapabilityEnquiry ::= SEQUENCE {
 rrc-TransactionIdentifier RRC-TransactionIdentifier,
 criticalExtensions CHOICE {
 c1 CHOICE {
 ueCapabilityEnquiry-r8 UECapabilityEnquiry-r8-IEs,
 spare3 NULL, spare2 NULL, spare1 NULL
 },
 criticalExtensionsFuture SEQUENCE {}
 }
}
UECapabilityEnquiry-r8-IEs ::= SEQUENCE {
 ue-CapabilityRequest UE-CapabilityRequest,
 nonCriticalExtension UECapabilityEnquiry-v8a0-IEs OPTIONAL
}
UECapabilityEnquiry-v8a0-IEs ::= SEQUENCE {
 lateNonCriticalExtension OCTET STRING OPTIONAL,
 nonCriticalExtension UECapabilityEnquiry-v1180-IEs OPTIONAL 
ETSI
3GPP TS 36.331 version 11.17.0 Release 11 193 ETSI TS 136 331 V11.17.0 (2017-02)
}
UECapabilityEnquiry-v1180-IEs ::= SEQUENCE {
 requestedFrequencyBands-r11 SEQUENCE (SIZE (1..16)) OF FreqBandIndicator-r11
 OPTIONAL,
 nonCriticalExtension SEQUENCE {} OPTIONAL
}
UE-CapabilityRequest ::= SEQUENCE (SIZE (1..maxRAT-Capabilities)) OF RAT-Type
UECapabilityInformation ::= SEQUENCE {
 rrc-TransactionIdentifier RRC-TransactionIdentifier,
 criticalExtensions CHOICE {
 c1 CHOICE{
 ueCapabilityInformation-r8 UECapabilityInformation-r8-IEs,
 spare7 NULL,
 spare6 NULL, spare5 NULL, spare4 NULL,
 spare3 NULL, spare2 NULL, spare1 NULL
 },
 criticalExtensionsFuture SEQUENCE {} 
ETSI
3GPP TS 36.331 version 11.17.0 Release 11 194 ETSI TS 136 331 V11.17.0 (2017-02)
 }
}
UECapabilityInformation-r8-IEs ::= SEQUENCE {
 ue-CapabilityRAT-ContainerList UE-CapabilityRAT-ContainerList,
 nonCriticalExtension UECapabilityInformation-v8a0-IEs OPTIONAL
}
UECapabilityInformation-v8a0-IEs ::= SEQUENCE {
 lateNonCriticalExtension OCTET STRING OPTIONAL,
 nonCriticalExtension SEQUENCE {} OPTIONAL
}
UEInformationRequest-r9 ::= SEQUENCE {
 rrc-TransactionIdentifier RRC-TransactionIdentifier,
 criticalExtensions CHOICE {
 c1 CHOICE {
 ueInformationRequest-r9 UEInformationRequest-r9-IEs,
 spare3 NULL, spare2 NULL, spare1 NULL
 },
 criticalExtensionsFuture SEQUENCE {}
 }
} 
ETSI
3GPP TS 36.331 version 11.17.0 Release 11 195 ETSI TS 136 331 V11.17.0 (2017-02)
UEInformationRequest-r9-IEs ::= SEQUENCE {
 rach-ReportReq-r9 BOOLEAN,
 rlf-ReportReq-r9 BOOLEAN,
 nonCriticalExtension UEInformationRequest-v930-IEs OPTIONAL
}
UEInformationRequest-v930-IEs ::= SEQUENCE {
 lateNonCriticalExtension OCTET STRING OPTIONAL,
 nonCriticalExtension UEInformationRequest-v1020-IEs OPTIONAL
}
UEInformationRequest-v1020-IEs ::= SEQUENCE {
 logMeasReportReq-r10 ENUMERATED {true} OPTIONAL, -- Need ON
 nonCriticalExtension UEInformationRequest-v1130-IEs OPTIONAL
}
UEInformationRequest-v1130-IEs ::= SEQUENCE {
 connEstFailReportReq-r11 ENUMERATED {true} OPTIONAL, -- Need ON
 nonCriticalExtension SEQUENCE {} OPTIONAL
}
ETSI
3GPP TS 36.331 version 11.17.0 Release 11 196 ETSI TS 136 331 V11.17.0 (2017-02)
UEInformationResponse-r9 ::= SEQUENCE {
 rrc-TransactionIdentifier RRC-TransactionIdentifier,
 criticalExtensions CHOICE {
 c1 CHOICE {
 ueInformationResponse-r9 UEInformationResponse-r9-IEs,
 spare3 NULL, spare2 NULL, spare1 NULL
 },
 criticalExtensionsFuture SEQUENCE {}
 }
}
UEInformationResponse-r9-IEs ::= SEQUENCE {
 rach-Report-r9 SEQUENCE {
 numberOfPreamblesSent-r9 NumberOfPreamblesSent-r11,
 contentionDetected-r9 BOOLEAN
 } OPTIONAL,
 rlf-Report-r9 RLF-Report-r9 OPTIONAL,
 nonCriticalExtension UEInformationResponse-v930-IEs OPTIONAL
}
-- Late non critical extensions
UEInformationResponse-v9e0-IEs ::= SEQUENCE {
 rlf-Report-v9e0 RLF-Report-v9e0 OPTIONAL,
 nonCriticalExtension SEQUENCE {} OPTIONAL
}
-- Regular non critical extensions
UEInformationResponse-v930-IEs ::= SEQUENCE {
 lateNonCriticalExtension OCTET STRING (CONTAINING UEInformationResponse-v9e0-IEs)
 OPTIONAL,
 nonCriticalExtension UEInformationResponse-v1020-IEs OPTIONAL
}
UEInformationResponse-v1020-IEs ::= SEQUENCE { 
ETSI
3GPP TS 36.331 version 11.17.0 Release 11 197 ETSI TS 136 331 V11.17.0 (2017-02)
 logMeasReport-r10 LogMeasReport-r10 OPTIONAL,
 nonCriticalExtension UEInformationResponse-v1130-IEs OPTIONAL
}
UEInformationResponse-v1130-IEs ::= SEQUENCE {
 connEstFailReport-r11 ConnEstFailReport-r11 OPTIONAL,
 nonCriticalExtension SEQUENCE {} OPTIONAL
}
RLF-Report-r9 ::= SEQUENCE {
 measResultLastServCell-r9 SEQUENCE {
 rsrpResult-r9 RSRP-Range,
 rsrqResult-r9 RSRQ-Range OPTIONAL
 },
 measResultNeighCells-r9 SEQUENCE {
 measResultListEUTRA-r9 MeasResultList2EUTRA-r9 OPTIONAL,
 measResultListUTRA-r9 MeasResultList2UTRA-r9 OPTIONAL,
 measResultListGERAN-r9 MeasResultListGERAN OPTIONAL,
 measResultsCDMA2000-r9 MeasResultList2CDMA2000-r9 OPTIONAL
 } OPTIONAL,
 ...,
 [[ locationInfo-r10 LocationInfo-r10 OPTIONAL,
 failedPCellId-r10 CHOICE {
 cellGlobalId-r10 CellGlobalIdEUTRA,
 pci-arfcn-r10 SEQUENCE {
 physCellId-r10 PhysCellId,
 carrierFreq-r10 ARFCN-ValueEUTRA
 }
 } OPTIONAL,
 reestablishmentCellId-r10 CellGlobalIdEUTRA OPTIONAL,
 timeConnFailure-r10 INTEGER (0..1023) OPTIONAL,
 connectionFailureType-r10 ENUMERATED {rlf, hof} OPTIONAL,
 previousPCellId-r10 CellGlobalIdEUTRA OPTIONAL
 ]],
 [[ failedPCellId-v1090 SEQUENCE { 
ETSI
3GPP TS 36.331 version 11.17.0 Release 11 198 ETSI TS 136 331 V11.17.0 (2017-02)
 carrierFreq-v1090 ARFCN-ValueEUTRA-v9e0
 } OPTIONAL
 ]],
 [[ basicFields-r11 SEQUENCE {
 c-RNTI-r11 C-RNTI,
 rlf-Cause-r11 ENUMERATED {
 t310-Expiry, randomAccessProblem,
 rlc-MaxNumRetx, spare1},
 timeSinceFailure-r11 TimeSinceFailure-r11
 } OPTIONAL,
 previousUTRA-CellId-r11 SEQUENCE {
 carrierFreq-r11 ARFCN-ValueUTRA,
 physCellId-r11 CHOICE {
 fdd-r11 PhysCellIdUTRA-FDD,
 tdd-r11 PhysCellIdUTRA-TDD
 },
 cellGlobalId-r11 CellGlobalIdUTRA OPTIONAL
 } OPTIONAL,
 selectedUTRA-CellId-r11 SEQUENCE {
 carrierFreq-r11 ARFCN-ValueUTRA,
 physCellId-r11 CHOICE {
 fdd-r11 PhysCellIdUTRA-FDD,
 tdd-r11 PhysCellIdUTRA-TDD
 }
 } OPTIONAL
 ]]
}
RLF-Report-v9e0 ::= SEQUENCE {
 measResultListEUTRA-v9e0 MeasResultList2EUTRA-v9e0
}
MeasResultList2EUTRA-r9 ::= SEQUENCE (SIZE (1..maxFreq)) OF MeasResult2EUTRA-r9
MeasResultList2EUTRA-v9e0 ::= SEQUENCE (SIZE (1..maxFreq)) OF MeasResult2EUTRA-v9e0 
ETSI
3GPP TS 36.331 version 11.17.0 Release 11 199 ETSI TS 136 331 V11.17.0 (2017-02)
MeasResult2EUTRA-r9 ::= SEQUENCE {
 carrierFreq-r9 ARFCN-ValueEUTRA,
 measResultList-r9 MeasResultListEUTRA
}
MeasResult2EUTRA-v9e0 ::= SEQUENCE {
 carrierFreq-v9e0 ARFCN-ValueEUTRA-v9e0 OPTIONAL
}
MeasResultList2UTRA-r9 ::= SEQUENCE (SIZE (1..maxFreq)) OF MeasResult2UTRA-r9
MeasResult2UTRA-r9 ::= SEQUENCE {
 carrierFreq-r9 ARFCN-ValueUTRA,
 measResultList-r9 MeasResultListUTRA
}
MeasResultList2CDMA2000-r9 ::= SEQUENCE (SIZE (1..maxFreq)) OF MeasResult2CDMA2000-r9
MeasResult2CDMA2000-r9 ::= SEQUENCE {
 carrierFreq-r9 CarrierFreqCDMA2000,
 measResultList-r9 MeasResultsCDMA2000
}
LogMeasReport-r10 ::= SEQUENCE {
 absoluteTimeStamp-r10 AbsoluteTimeInfo-r10,
 traceReference-r10 TraceReference-r10,
 traceRecordingSessionRef-r10 OCTET STRING (SIZE (2)),
 tce-Id-r10 OCTET STRING (SIZE (1)),
 logMeasInfoList-r10 LogMeasInfoList-r10,
 logMeasAvailable-r10 ENUMERATED {true} OPTIONAL,
 ...
}
LogMeasInfoList-r10 ::= SEQUENCE (SIZE (1..maxLogMeasReport-r10)) OF LogMeasInfo-r10 
ETSI
3GPP TS 36.331 version 11.17.0 Release 11 200 ETSI TS 136 331 V11.17.0 (2017-02)
LogMeasInfo-r10 ::= SEQUENCE {
 locationInfo-r10 LocationInfo-r10 OPTIONAL,
 relativeTimeStamp-r10 INTEGER (0..7200),
 servCellIdentity-r10 CellGlobalIdEUTRA,
 measResultServCell-r10 SEQUENCE {
 rsrpResult-r10 RSRP-Range,
 rsrqResult-r10 RSRQ-Range
 },
 measResultNeighCells-r10 SEQUENCE {
 measResultListEUTRA-r10 MeasResultList2EUTRA-r9 OPTIONAL,
 measResultListUTRA-r10 MeasResultList2UTRA-r9 OPTIONAL,
 measResultListGERAN-r10 MeasResultList2GERAN-r10 OPTIONAL,
 measResultListCDMA2000-r10 MeasResultList2CDMA2000-r9 OPTIONAL
 } OPTIONAL,
 ...,
 [[ measResultListEUTRA-v1090 MeasResultList2EUTRA-v9e0 OPTIONAL
 ]]
}
MeasResultList2GERAN-r10 ::= SEQUENCE (SIZE (1..maxCellListGERAN)) OF MeasResultListGERAN
ConnEstFailReport-r11 ::= SEQUENCE {
 failedCellId-r11 CellGlobalIdEUTRA,
 locationInfo-r11 LocationInfo-r10 OPTIONAL,
 measResultFailedCell-r11 SEQUENCE {
 rsrpResult-r11 RSRP-Range,
 rsrqResult-r11 RSRQ-Range OPTIONAL
 },
 measResultNeighCells-r11 SEQUENCE {
 measResultListEUTRA-r11 MeasResultList2EUTRA-r9 OPTIONAL,
 measResultListUTRA-r11 MeasResultList2UTRA-r9 OPTIONAL,
 measResultListGERAN-r11 MeasResultListGERAN OPTIONAL,
 measResultsCDMA2000-r11 MeasResultList2CDMA2000-r9 OPTIONAL
 } OPTIONAL, 
ETSI
3GPP TS 36.331 version 11.17.0 Release 11 201 ETSI TS 136 331 V11.17.0 (2017-02)
 numberOfPreamblesSent-r11 NumberOfPreamblesSent-r11,
 contentionDetected-r11 BOOLEAN,
 maxTxPowerReached-r11 BOOLEAN,
 timeSinceFailure-r11 TimeSinceFailure-r11,
 measResultListEUTRA-v1130 MeasResultList2EUTRA-v9e0 OPTIONAL,
 ...
}
NumberOfPreamblesSent-r11::= INTEGER (1..200)
TimeSinceFailure-r11 ::= INTEGER (0..172800)
ULHandoverPreparationTransfer ::= SEQUENCE {
 criticalExtensions CHOICE {
 c1 CHOICE {
 ulHandoverPreparationTransfer-r8 ULHandoverPreparationTransfer-r8-IEs,
 spare3 NULL, spare2 NULL, spare1 NULL
 },
 criticalExtensionsFuture SEQUENCE {}
 }
}
ULHandoverPreparationTransfer-r8-IEs ::= SEQUENCE {
 cdma2000-Type CDMA2000-Type,
 meid BIT STRING (SIZE (56)) OPTIONAL,
 dedicatedInfo DedicatedInfoCDMA2000,
 nonCriticalExtension ULHandoverPreparationTransfer-v8a0-IEs OPTIONAL
}
ULHandoverPreparationTransfer-v8a0-IEs ::= SEQUENCE {
 lateNonCriticalExtension OCTET STRING OPTIONAL,
 nonCriticalExtension SEQUENCE {} OPTIONAL
}
ULInformationTransfer ::= SEQUENCE {
 criticalExtensions CHOICE {
 c1 CHOICE {
 ulInformationTransfer-r8 ULInformationTransfer-r8-IEs,
 spare3 NULL, spare2 NULL, spare1 NULL
 },
 criticalExtensionsFuture SEQUENCE {}
 }
}
ULInformationTransfer-r8-IEs ::= SEQUENCE {
 dedicatedInfoType CHOICE {
 dedicatedInfoNAS DedicatedInfoNAS,
 dedicatedInfoCDMA2000-1XRTT DedicatedInfoCDMA2000,
 dedicatedInfoCDMA2000-HRPD DedicatedInfoCDMA2000
 },
 nonCriticalExtension ULInformationTransfer-v8a0-IEs OPTIONAL
}
ULInformationTransfer-v8a0-IEs ::= SEQUENCE {
 lateNonCriticalExtension OCTET STRING OPTIONAL,
 nonCriticalExtension SEQUENCE {} OPTIONAL 
ETSI
3GPP TS 36.331 version 11.17.0 Release 11 205 ETSI TS 136 331 V11.17.0 (2017-02)
}
SystemInformationBlockType2 ::= SEQUENCE {
 ac-BarringInfo SEQUENCE {
 ac-BarringForEmergency BOOLEAN,
 ac-BarringForMO-Signalling AC-BarringConfig OPTIONAL, -- Need OP
 ac-BarringForMO-Data AC-BarringConfig OPTIONAL -- Need OP
 } OPTIONAL, -- Need OP
 radioResourceConfigCommon RadioResourceConfigCommonSIB,
 ue-TimersAndConstants UE-TimersAndConstants,
 freqInfo SEQUENCE {
 ul-CarrierFreq ARFCN-ValueEUTRA OPTIONAL, -- Need OP
 ul-Bandwidth ENUMERATED {n6, n15, n25, n50, n75, n100}
 OPTIONAL, -- Need OP
 additionalSpectrumEmission AdditionalSpectrumEmission
 },
 mbsfn-SubframeConfigList MBSFN-SubframeConfigList OPTIONAL, -- Need OR
 timeAlignmentTimerCommon TimeAlignmentTimer,
 ...,
 lateNonCriticalExtension OCTET STRING (CONTAINING SystemInformationBlockType2-v8h0-IEs)
 OPTIONAL,
 [[ ssac-BarringForMMTEL-Voice-r9 AC-BarringConfig OPTIONAL, -- Need OP
 ssac-BarringForMMTEL-Video-r9 AC-BarringConfig OPTIONAL -- Need OP 
ETSI
3GPP TS 36.331 version 11.17.0 Release 11 206 ETSI TS 136 331 V11.17.0 (2017-02)
 ]],
 [[ ac-BarringForCSFB-r10 AC-BarringConfig OPTIONAL -- Need OP
 ]]
}
SystemInformationBlockType2-v8h0-IEs ::= SEQUENCE {
 multiBandInfoList SEQUENCE (SIZE (1..maxMultiBands)) OF AdditionalSpectrumEmission
 OPTIONAL, -- Need OR
 nonCriticalExtension SystemInformationBlockType2-v9e0-IEs OPTIONAL
}
SystemInformationBlockType2-v9e0-IEs ::= SEQUENCE {
 ul-CarrierFreq-v9e0 ARFCN-ValueEUTRA-v9e0 OPTIONAL, -- Cond ul-FreqMax
 nonCriticalExtension SEQUENCE {} OPTIONAL
}
AC-BarringConfig ::= SEQUENCE {
 ac-BarringFactor ENUMERATED {
 p00, p05, p10, p15, p20, p25, p30, p40,
 p50, p60, p70, p75, p80, p85, p90, p95},
 ac-BarringTime ENUMERATED {s4, s8, s16, s32, s64, s128, s256, s512},
 ac-BarringForSpecialAC BIT STRING (SIZE(5))
}
MBSFN-SubframeConfigList ::= SEQUENCE (SIZE (1..maxMBSFN-Allocations)) OF MBSFN-SubframeConfig
SystemInformationBlockType3 ::= SEQUENCE {
 cellReselectionInfoCommon SEQUENCE {
 q-Hyst ENUMERATED {
 dB0, dB1, dB2, dB3, dB4, dB5, dB6, dB8, dB10,
 dB12, dB14, dB16, dB18, dB20, dB22, dB24}, 
ETSI
3GPP TS 36.331 version 11.17.0 Release 11 208 ETSI TS 136 331 V11.17.0 (2017-02)
 speedStateReselectionPars SEQUENCE {
 mobilityStateParameters MobilityStateParameters,
 q-HystSF SEQUENCE {
 sf-Medium ENUMERATED {
 dB-6, dB-4, dB-2, dB0},
 sf-High ENUMERATED {
 dB-6, dB-4, dB-2, dB0}
 }
 } OPTIONAL -- Need OP
 },
 cellReselectionServingFreqInfo SEQUENCE {
 s-NonIntraSearch ReselectionThreshold OPTIONAL, -- Need OP
 threshServingLow ReselectionThreshold,
 cellReselectionPriority CellReselectionPriority
 },
 intraFreqCellReselectionInfo SEQUENCE {
 q-RxLevMin Q-RxLevMin,
 p-Max P-Max OPTIONAL, -- Need OP
 s-IntraSearch ReselectionThreshold OPTIONAL, -- Need OP
 allowedMeasBandwidth AllowedMeasBandwidth OPTIONAL, -- Need OP
 presenceAntennaPort1 PresenceAntennaPort1,
 neighCellConfig NeighCellConfig,
 t-ReselectionEUTRA T-Reselection,
 t-ReselectionEUTRA-SF SpeedStateScaleFactors OPTIONAL -- Need OP
 },
 ...,
 lateNonCriticalExtension OCTET STRING (CONTAINING SystemInformationBlockType3-v10j0-
IEs) OPTIONAL,
 [[ s-IntraSearch-v920 SEQUENCE {
 s-IntraSearchP-r9 ReselectionThreshold,
 s-IntraSearchQ-r9 ReselectionThresholdQ-r9
 } OPTIONAL, -- Need OP
 s-NonIntraSearch-v920 SEQUENCE {
 s-NonIntraSearchP-r9 ReselectionThreshold,
 s-NonIntraSearchQ-r9 ReselectionThresholdQ-r9 
ETSI
3GPP TS 36.331 version 11.17.0 Release 11 209 ETSI TS 136 331 V11.17.0 (2017-02)
 } OPTIONAL, -- Need OP
 q-QualMin-r9 Q-QualMin-r9 OPTIONAL, -- Need OP
 threshServingLowQ-r9 ReselectionThresholdQ-r9 OPTIONAL -- Need OP
 ]],
 [[ q-QualMinWB-r11 Q-QualMin-r9 OPTIONAL -- Cond WB-RSRQ
 ]]
}
-- Late non critical extensions
SystemInformationBlockType3-v10j0-IEs ::= SEQUENCE {
 freqBandInfo-r10 NS-PmaxList-r10 OPTIONAL, -- Need OR
 multiBandInfoList-v10j0 MultiBandInfoList-v10j0 OPTIONAL, -- Need OR
 nonCriticalExtension SEQUENCE {} OPTIONAL
}
SystemInformationBlockType4 ::= SEQUENCE {
 intraFreqNeighCellList IntraFreqNeighCellList OPTIONAL, -- Need OR
 intraFreqBlackCellList IntraFreqBlackCellList OPTIONAL, -- Need OR
 csg-PhysCellIdRange PhysCellIdRange OPTIONAL, -- Cond CSG
 ...,
 lateNonCriticalExtension OCTET STRING OPTIONAL
}
IntraFreqNeighCellList ::= SEQUENCE (SIZE (1..maxCellIntra)) OF IntraFreqNeighCellInfo
IntraFreqNeighCellInfo ::= SEQUENCE {
 physCellId PhysCellId,
 q-OffsetCell Q-OffsetRange,
 ...
}
IntraFreqBlackCellList ::= SEQUENCE (SIZE (1..maxCellBlack)) OF PhysCellIdRange
SystemInformationBlockType5 ::= SEQUENCE {
 interFreqCarrierFreqList InterFreqCarrierFreqList,
 ...,
 lateNonCriticalExtension OCTET STRING (CONTAINING SystemInformationBlockType5-v8h0-IEs)
 OPTIONAL
}
SystemInformationBlockType5-v8h0-IEs ::= SEQUENCE {
 interFreqCarrierFreqList-v8h0 SEQUENCE (SIZE (1..maxFreq)) OF InterFreqCarrierFreqInfo-v8h0
OPTIONAL, -- Need OP
 nonCriticalExtension SystemInformationBlockType5-v9e0-IEs OPTIONAL
}
SystemInformationBlockType5-v9e0-IEs ::= SEQUENCE {
 interFreqCarrierFreqList-v9e0 SEQUENCE (SIZE (1..maxFreq)) OF InterFreqCarrierFreqInfo-v9e0
 OPTIONAL, -- Need OR
 nonCriticalExtension SystemInformationBlockType5-v10j0-IEs OPTIONAL
}
SystemInformationBlockType5-v10j0-IEs ::= SEQUENCE { 
ETSI
3GPP TS 36.331 version 11.17.0 Release 11 213 ETSI TS 136 331 V11.17.0 (2017-02)
 interFreqCarrierFreqList-v10j0 SEQUENCE (SIZE (1..maxFreq)) OF InterFreqCarrierFreqInfo-v10j0
 OPTIONAL, -- Need OR
 nonCriticalExtension SEQUENCE {} OPTIONAL
}
InterFreqCarrierFreqList ::= SEQUENCE (SIZE (1..maxFreq)) OF InterFreqCarrierFreqInfo
InterFreqCarrierFreqInfo ::= SEQUENCE {
 dl-CarrierFreq ARFCN-ValueEUTRA,
 q-RxLevMin Q-RxLevMin,
 p-Max P-Max OPTIONAL, -- Need OP
 t-ReselectionEUTRA T-Reselection,
 t-ReselectionEUTRA-SF SpeedStateScaleFactors OPTIONAL, -- Need OP
 threshX-High ReselectionThreshold,
 threshX-Low ReselectionThreshold,
 allowedMeasBandwidth AllowedMeasBandwidth,
 presenceAntennaPort1 PresenceAntennaPort1,
 cellReselectionPriority CellReselectionPriority OPTIONAL, -- Need OP
 neighCellConfig NeighCellConfig,
 q-OffsetFreq Q-OffsetRange DEFAULT dB0,
 interFreqNeighCellList InterFreqNeighCellList OPTIONAL, -- Need OR
 interFreqBlackCellList InterFreqBlackCellList OPTIONAL, -- Need OR
 ...,
 [[ q-QualMin-r9 Q-QualMin-r9 OPTIONAL, -- Need OP
 threshX-Q-r9 SEQUENCE {
 threshX-HighQ-r9 ReselectionThresholdQ-r9,
 threshX-LowQ-r9 ReselectionThresholdQ-r9
 } OPTIONAL -- Cond RSRQ
 ]],
 [[ q-QualMinWB-r11 Q-QualMin-r9 OPTIONAL -- Cond WB-RSRQ
 ]]
}
InterFreqCarrierFreqInfo-v8h0 ::= SEQUENCE {
 multiBandInfoList MultiBandInfoList OPTIONAL -- Need OR 
ETSI
3GPP TS 36.331 version 11.17.0 Release 11 214 ETSI TS 136 331 V11.17.0 (2017-02)
}
InterFreqCarrierFreqInfo-v9e0 ::= SEQUENCE {
 dl-CarrierFreq-v9e0 ARFCN-ValueEUTRA-v9e0 OPTIONAL, -- Cond dl-FreqMax
 multiBandInfoList-v9e0 MultiBandInfoList-v9e0 OPTIONAL -- Need OR
}
InterFreqCarrierFreqInfo-v10j0 ::= SEQUENCE {
 freqBandInfo-r10 NS-PmaxList-r10 OPTIONAL, -- Need OR
 multiBandInfoList-v10j0 MultiBandInfoList-v10j0 OPTIONAL -- Need OR
}
InterFreqNeighCellList ::= SEQUENCE (SIZE (1..maxCellInter)) OF InterFreqNeighCellInfo
InterFreqNeighCellInfo ::= SEQUENCE {
 physCellId PhysCellId,
 q-OffsetCell Q-OffsetRange
}
InterFreqBlackCellList ::= SEQUENCE (SIZE (1..maxCellBlack)) OF PhysCellIdRange
SystemInformationBlockType6 ::= SEQUENCE {
 carrierFreqListUTRA-FDD CarrierFreqListUTRA-FDD OPTIONAL, -- Need OR
 carrierFreqListUTRA-TDD CarrierFreqListUTRA-TDD OPTIONAL, -- Need OR
 t-ReselectionUTRA T-Reselection,
 t-ReselectionUTRA-SF SpeedStateScaleFactors OPTIONAL, -- Need OP
 ...,
 lateNonCriticalExtension OCTET STRING (CONTAINING SystemInformationBlockType6-v8h0-IEs)
 OPTIONAL
}
SystemInformationBlockType6-v8h0-IEs ::= SEQUENCE {
 carrierFreqListUTRA-FDD-v8h0 SEQUENCE (SIZE (1..maxUTRA-FDD-Carrier)) OF CarrierFreqInfoUTRAFDD-v8h0
OPTIONAL, -- Cond UTRA-FDD
 nonCriticalExtension SEQUENCE {} OPTIONAL
}
CarrierFreqListUTRA-FDD ::= SEQUENCE (SIZE (1..maxUTRA-FDD-Carrier)) OF CarrierFreqUTRA-FDD
CarrierFreqUTRA-FDD ::= SEQUENCE {
 carrierFreq ARFCN-ValueUTRA,
 cellReselectionPriority CellReselectionPriority OPTIONAL, -- Need OP
 threshX-High ReselectionThreshold,
 threshX-Low ReselectionThreshold,
 q-RxLevMin INTEGER (-60..-13), 
ETSI
3GPP TS 36.331 version 11.17.0 Release 11 217 ETSI TS 136 331 V11.17.0 (2017-02)
 p-MaxUTRA INTEGER (-50..33),
 q-QualMin INTEGER (-24..0),
 ...,
 [[ threshX-Q-r9 SEQUENCE {
 threshX-HighQ-r9 ReselectionThresholdQ-r9,
 threshX-LowQ-r9 ReselectionThresholdQ-r9
 } OPTIONAL -- Cond RSRQ
 ]]
}
CarrierFreqInfoUTRA-FDD-v8h0 ::= SEQUENCE {
 multiBandInfoList SEQUENCE (SIZE (1..maxMultiBands)) OF FreqBandIndicator-UTRA-FDD
 OPTIONAL -- Need OR
}
CarrierFreqListUTRA-TDD ::= SEQUENCE (SIZE (1..maxUTRA-TDD-Carrier)) OF CarrierFreqUTRA-TDD
CarrierFreqUTRA-TDD ::= SEQUENCE {
 carrierFreq ARFCN-ValueUTRA,
 cellReselectionPriority CellReselectionPriority OPTIONAL, -- Need OP
 threshX-High ReselectionThreshold,
 threshX-Low ReselectionThreshold,
 q-RxLevMin INTEGER (-60..-13),
 p-MaxUTRA INTEGER (-50..33),
 ...
}
FreqBandIndicator-UTRA-FDD ::= INTEGER (1..86)
SystemInformationBlockType7 ::= SEQUENCE {
 t-ReselectionGERAN T-Reselection,
 t-ReselectionGERAN-SF SpeedStateScaleFactors OPTIONAL, -- Need OR
 carrierFreqsInfoList CarrierFreqsInfoListGERAN OPTIONAL, -- Need OR
 ...,
 lateNonCriticalExtension OCTET STRING OPTIONAL
} 
ETSI
3GPP TS 36.331 version 11.17.0 Release 11 219 ETSI TS 136 331 V11.17.0 (2017-02)
CarrierFreqsInfoListGERAN ::= SEQUENCE (SIZE (1..maxGNFG)) OF CarrierFreqsInfoGERAN
CarrierFreqsInfoGERAN ::= SEQUENCE {
 carrierFreqs CarrierFreqsGERAN,
 commonInfo SEQUENCE {
 cellReselectionPriority CellReselectionPriority OPTIONAL, -- Need OP
 ncc-Permitted BIT STRING (SIZE (8)),
 q-RxLevMin INTEGER (0..45),
 p-MaxGERAN INTEGER (0..39) OPTIONAL, -- Need OP
 threshX-High ReselectionThreshold,
 threshX-Low ReselectionThreshold
 },
 ...
}
SystemInformationBlockType8 ::= SEQUENCE {
 systemTimeInfo SystemTimeInfoCDMA2000 OPTIONAL, -- Need OR
 searchWindowSize INTEGER (0..15) OPTIONAL, -- Need OR
 parametersHRPD SEQUENCE {
 preRegistrationInfoHRPD PreRegistrationInfoHRPD,
 cellReselectionParametersHRPD CellReselectionParametersCDMA2000 OPTIONAL -- Need OR
 } OPTIONAL, -- Need OR
 parameters1XRTT SEQUENCE {
 csfb-RegistrationParam1XRTT CSFB-RegistrationParam1XRTT OPTIONAL, -- Need OP
 longCodeState1XRTT BIT STRING (SIZE (42)) OPTIONAL, -- Need OR
 cellReselectionParameters1XRTT CellReselectionParametersCDMA2000 OPTIONAL -- Need OR
 } OPTIONAL, -- Need OR
 ...,
 lateNonCriticalExtension OCTET STRING OPTIONAL,
 [[ csfb-SupportForDualRxUEs-r9 BOOLEAN OPTIONAL, -- Need OR
 cellReselectionParametersHRPD-v920 CellReselectionParametersCDMA2000-v920 OPTIONAL, -- Cond
NCL-HRPD
 cellReselectionParameters1XRTT-v920 CellReselectionParametersCDMA2000-v920 OPTIONAL, -- Cond
NCL-1XRTT
 csfb-RegistrationParam1XRTT-v920 CSFB-RegistrationParam1XRTT-v920 OPTIONAL, -- Cond
REG-1XRTT
 ac-BarringConfig1XRTT-r9 AC-BarringConfig1XRTT-r9 OPTIONAL -- Cond REG-1XRTT
 ]],
 [[ csfb-DualRxTxSupport-r10 ENUMERATED {true} OPTIONAL -- Cond REG-1XRTT
 ]],
 [[ sib8-PerPLMN-List-r11 SIB8-PerPLMN-List-r11 OPTIONAL -- Need OR
 ]]
}
CellReselectionParametersCDMA2000 ::= SEQUENCE { 
ETSI
3GPP TS 36.331 version 11.17.0 Release 11 221 ETSI TS 136 331 V11.17.0 (2017-02)
 bandClassList BandClassListCDMA2000,
 neighCellList NeighCellListCDMA2000,
t-ReselectionCDMA2000 T-Reselection,
 t-ReselectionCDMA2000-SF SpeedStateScaleFactors OPTIONAL -- Need OP
}
CellReselectionParametersCDMA2000-r11 ::= SEQUENCE {
 bandClassList BandClassListCDMA2000,
 neighCellList-r11 SEQUENCE (SIZE (1..16)) OF NeighCellCDMA2000-r11,
t-ReselectionCDMA2000 T-Reselection,
 t-ReselectionCDMA2000-SF SpeedStateScaleFactors OPTIONAL -- Need OP
}
CellReselectionParametersCDMA2000-v920 ::= SEQUENCE {
 neighCellList-v920 NeighCellListCDMA2000-v920
}
NeighCellListCDMA2000 ::= SEQUENCE (SIZE (1..16)) OF NeighCellCDMA2000
NeighCellCDMA2000 ::= SEQUENCE {
 bandClass BandclassCDMA2000,
 neighCellsPerFreqList NeighCellsPerBandclassListCDMA2000
}
NeighCellCDMA2000-r11 ::= SEQUENCE {
 bandClass BandclassCDMA2000,
 neighFreqInfoList-r11 SEQUENCE (SIZE (1..16)) OF NeighCellsPerBandclassCDMA2000-r11
}
NeighCellsPerBandclassListCDMA2000 ::= SEQUENCE (SIZE (1..16)) OF NeighCellsPerBandclassCDMA2000
NeighCellsPerBandclassCDMA2000 ::= SEQUENCE {
 arfcn ARFCN-ValueCDMA2000,
 physCellIdList PhysCellIdListCDMA2000
} 
ETSI
3GPP TS 36.331 version 11.17.0 Release 11 222 ETSI TS 136 331 V11.17.0 (2017-02)
NeighCellsPerBandclassCDMA2000-r11 ::= SEQUENCE {
 arfcn ARFCN-ValueCDMA2000,
 physCellIdList-r11 SEQUENCE (SIZE (1..40)) OF PhysCellIdCDMA2000
}
NeighCellListCDMA2000-v920 ::= SEQUENCE (SIZE (1..16)) OF NeighCellCDMA2000-v920
NeighCellCDMA2000-v920 ::= SEQUENCE {
 neighCellsPerFreqList-v920 NeighCellsPerBandclassListCDMA2000-v920
}
NeighCellsPerBandclassListCDMA2000-v920 ::= SEQUENCE (SIZE (1..16)) OF
NeighCellsPerBandclassCDMA2000-v920
NeighCellsPerBandclassCDMA2000-v920 ::= SEQUENCE {
 physCellIdList-v920 PhysCellIdListCDMA2000-v920
}
PhysCellIdListCDMA2000 ::= SEQUENCE (SIZE (1..16)) OF PhysCellIdCDMA2000
PhysCellIdListCDMA2000-v920 ::= SEQUENCE (SIZE (0..24)) OF PhysCellIdCDMA2000
BandClassListCDMA2000 ::= SEQUENCE (SIZE (1..maxCDMA-BandClass)) OF BandClassInfoCDMA2000
BandClassInfoCDMA2000 ::= SEQUENCE {
 bandClass BandclassCDMA2000,
 cellReselectionPriority CellReselectionPriority OPTIONAL, -- Need OP
 threshX-High INTEGER (0..63),
 threshX-Low INTEGER (0..63),
 ...
}
AC-BarringConfig1XRTT-r9 ::= SEQUENCE {
 ac-Barring0to9-r9 INTEGER (0..63), 
ETSI
3GPP TS 36.331 version 11.17.0 Release 11 223 ETSI TS 136 331 V11.17.0 (2017-02)
 ac-Barring10-r9 INTEGER (0..7),
 ac-Barring11-r9 INTEGER (0..7),
 ac-Barring12-r9 INTEGER (0..7),
 ac-Barring13-r9 INTEGER (0..7),
 ac-Barring14-r9 INTEGER (0..7),
 ac-Barring15-r9 INTEGER (0..7),
 ac-BarringMsg-r9 INTEGER (0..7),
 ac-BarringReg-r9 INTEGER (0..7),
 ac-BarringEmg-r9 INTEGER (0..7)
}
SIB8-PerPLMN-List-r11 ::= SEQUENCE (SIZE (1..maxPLMN-r11)) OF SIB8-PerPLMN-r11
SIB8-PerPLMN-r11 ::= SEQUENCE {
 plmn-Identity-r11 INTEGER (1..maxPLMN-r11),
 parametersCDMA2000-r11 CHOICE {
 explicitValue ParametersCDMA2000-r11,
 defaultValue NULL
 }
}
ParametersCDMA2000-r11 ::= SEQUENCE {
 systemTimeInfo-r11 CHOICE {
 explicitValue SystemTimeInfoCDMA2000,
 defaultValue NULL
 } OPTIONAL, -- Need OR
 searchWindowSize-r11 INTEGER (0..15),
 parametersHRPD-r11 SEQUENCE {
 preRegistrationInfoHRPD-r11 PreRegistrationInfoHRPD,
 cellReselectionParametersHRPD-r11 CellReselectionParametersCDMA2000-r11 OPTIONAL -- Need OR
 } OPTIONAL, -- Need OR
 parameters1XRTT-r11 SEQUENCE {
 csfb-RegistrationParam1XRTT-r11 CSFB-RegistrationParam1XRTT OPTIONAL, -- Need OP
 csfb-RegistrationParam1XRTT-Ext-r11 CSFB-RegistrationParam1XRTT-v920 OPTIONAL, -- Cond REG-
1XRTT-PerPLMN 
ETSI
3GPP TS 36.331 version 11.17.0 Release 11 224 ETSI TS 136 331 V11.17.0 (2017-02)
 longCodeState1XRTT-r11 BIT STRING (SIZE (42)) OPTIONAL, -- Cond PerPLMN-LC
 cellReselectionParameters1XRTT-r11 CellReselectionParametersCDMA2000-r11 OPTIONAL, -- Need OR
 ac-BarringConfig1XRTT-r11 AC-BarringConfig1XRTT-r9 OPTIONAL, -- Cond REG-
1XRTT-PerPLMN
 csfb-SupportForDualRxUEs-r11 BOOLEAN OPTIONAL, -- Need OR
 csfb-DualRxTxSupport-r11 ENUMERATED {true} OPTIONAL -- Cond REG-1XRTTPerPLMN

 } OPTIONAL, -- Need OR
 ...
}
SystemInformationBlockType9 ::= SEQUENCE {
 hnb-Name OCTET STRING (SIZE(1..48)) OPTIONAL, -- Need OR
 ...,
 lateNonCriticalExtension OCTET STRING OPTIONAL
}
SystemInformationBlockType10 ::= SEQUENCE {
 messageIdentifier BIT STRING (SIZE (16)),
 serialNumber BIT STRING (SIZE (16)),
 warningType OCTET STRING (SIZE (2)),
 dummy OCTET STRING (SIZE (50)) OPTIONAL, -- Need OP
 ...,
 lateNonCriticalExtension OCTET STRING OPTIONAL
}
ETSI
3GPP TS 36.331 version 11.17.0 Release 11 228 ETSI TS 136 331 V11.17.0 (2017-02)
SystemInformationBlockType11 ::= SEQUENCE {
 messageIdentifier BIT STRING (SIZE (16)),
 serialNumber BIT STRING (SIZE (16)),
 warningMessageSegmentType ENUMERATED {notLastSegment, lastSegment},
 warningMessageSegmentNumber INTEGER (0..63),
 warningMessageSegment OCTET STRING,
 dataCodingScheme OCTET STRING (SIZE (1)) OPTIONAL, -- Cond Segment1
 ...,
 lateNonCriticalExtension OCTET STRING OPTIONAL
}
ETSI
3GPP TS 36.331 version 11.17.0 Release 11 229 ETSI TS 136 331 V11.17.0 (2017-02)
SystemInformationBlockType12-r9 ::= SEQUENCE {
 messageIdentifier-r9 BIT STRING (SIZE (16)),
 serialNumber-r9 BIT STRING (SIZE (16)),
 warningMessageSegmentType-r9 ENUMERATED {notLastSegment, lastSegment},
 warningMessageSegmentNumber-r9 INTEGER (0..63),
 warningMessageSegment-r9 OCTET STRING,
 dataCodingScheme-r9 OCTET STRING (SIZE (1)) OPTIONAL, -- Cond Segment1
 lateNonCriticalExtension OCTET STRING OPTIONAL,
 ...
}
ETSI
3GPP TS 36.331 version 11.17.0 Release 11 230 ETSI TS 136 331 V11.17.0 (2017-02)
SystemInformationBlockType13-r9 ::= SEQUENCE {
 mbsfn-AreaInfoList-r9 MBSFN-AreaInfoList-r9,
 notificationConfig-r9 MBMS-NotificationConfig-r9,
 lateNonCriticalExtension OCTET STRING OPTIONAL,
 ...
}
SystemInformationBlockType14-r11 ::= SEQUENCE {
 eab-Param-r11 CHOICE {
 eab-Common-r11 EAB-Config-r11,
 eab-PerPLMN-List-r11 SEQUENCE (SIZE (1..maxPLMN-r11)) OF EAB-ConfigPLMN-r11
 } OPTIONAL, -- Need OR
 lateNonCriticalExtension OCTET STRING OPTIONAL,
 ...
}
EAB-ConfigPLMN-r11 ::= SEQUENCE {
 eab-Config-r11 EAB-Config-r11 OPTIONAL -- Need OR
}
EAB-Config-r11 ::= SEQUENCE {
 eab-Category-r11 ENUMERATED {a, b, c},
 eab-BarringBitmap-r11 BIT STRING (SIZE (10))
}
SystemInformationBlockType15-r11 ::= SEQUENCE {
 mbms-SAI-IntraFreq-r11 MBMS-SAI-List-r11 OPTIONAL, -- Need OR
 mbms-SAI-InterFreqList-r11 MBMS-SAI-InterFreqList-r11 OPTIONAL, -- Need OR
 lateNonCriticalExtension OCTET STRING OPTIONAL,
 ...,
 [[ mbms-SAI-InterFreqList-v1140 MBMS-SAI-InterFreqList-v1140 OPTIONAL -- Cond InterFreq
 ]]
}
MBMS-SAI-List-r11 ::= SEQUENCE (SIZE (1..maxSAI-MBMS-r11)) OF MBMS-SAI-r11
MBMS-SAI-r11 ::= INTEGER (0..65535)
MBMS-SAI-InterFreqList-r11 ::= SEQUENCE (SIZE (1..maxFreq)) OF MBMS-SAI-InterFreq-r11
MBMS-SAI-InterFreqList-v1140 ::= SEQUENCE (SIZE (1..maxFreq)) OF MBMS-SAI-InterFreq-v1140
MBMS-SAI-InterFreq-r11 ::= SEQUENCE {
 dl-CarrierFreq-r11 ARFCN-ValueEUTRA-r9,
 mbms-SAI-List-r11 MBMS-SAI-List-r11 
ETSI
3GPP TS 36.331 version 11.17.0 Release 11 232 ETSI TS 136 331 V11.17.0 (2017-02)
}
MBMS-SAI-InterFreq-v1140 ::= SEQUENCE {
 multiBandInfoList-r11 MultiBandInfoList-r11 OPTIONAL -- Need OR
}
SystemInformationBlockType16-r11 ::= SEQUENCE {
 timeInfo-r11 SEQUENCE {
 timeInfoUTC-r11 INTEGER (0..549755813887),
 dayLightSavingTime-r11 BIT STRING (SIZE (2)) OPTIONAL, -- Need OR
 leapSeconds-r11 INTEGER (-127..128) OPTIONAL, -- Need OR
 localTimeOffset-r11 INTEGER (-63..64) OPTIONAL -- Need OR
 } OPTIONAL, -- Need OR
 lateNonCriticalExtension OCTET STRING OPTIONAL, 
ETSI
3GPP TS 36.331 version 11.17.0 Release 11 233 ETSI TS 136 331 V11.17.0 (2017-02)
 ...
}
AntennaInfoCommon ::= SEQUENCE {
 antennaPortsCount ENUMERATED {an1, an2, an4, spare1}
}
AntennaInfoDedicated ::= SEQUENCE {
 transmissionMode ENUMERATED {
 tm1, tm2, tm3, tm4, tm5, tm6, 
ETSI
3GPP TS 36.331 version 11.17.0 Release 11 234 ETSI TS 136 331 V11.17.0 (2017-02)
 tm7, tm8-v920},
 codebookSubsetRestriction CHOICE {
 n2TxAntenna-tm3 BIT STRING (SIZE (2)),
 n4TxAntenna-tm3 BIT STRING (SIZE (4)),
 n2TxAntenna-tm4 BIT STRING (SIZE (6)),
 n4TxAntenna-tm4 BIT STRING (SIZE (64)),
 n2TxAntenna-tm5 BIT STRING (SIZE (4)),
 n4TxAntenna-tm5 BIT STRING (SIZE (16)),
 n2TxAntenna-tm6 BIT STRING (SIZE (4)),
 n4TxAntenna-tm6 BIT STRING (SIZE (16))
 } OPTIONAL, -- Cond TM
 ue-TransmitAntennaSelection CHOICE{
 release NULL,
 setup ENUMERATED {closedLoop, openLoop}
 }
}
AntennaInfoDedicated-v920 ::= SEQUENCE {
 codebookSubsetRestriction-v920 CHOICE {
 n2TxAntenna-tm8-r9 BIT STRING (SIZE (6)),
 n4TxAntenna-tm8-r9 BIT STRING (SIZE (32))
 } OPTIONAL -- Cond TM8
}
AntennaInfoDedicated-r10 ::= SEQUENCE {
 transmissionMode-r10 ENUMERATED {
 tm1, tm2, tm3, tm4, tm5, tm6, tm7, tm8-v920,
 tm9-v1020, tm10-v1130, spare6, spare5, spare4,
 spare3, spare2, spare1},
 codebookSubsetRestriction-r10 BIT STRING OPTIONAL, -- Cond TMX
 ue-TransmitAntennaSelection CHOICE{
 release NULL,
 setup ENUMERATED {closedLoop, openLoop}
 }
} 
ETSI
3GPP TS 36.331 version 11.17.0 Release 11 235 ETSI TS 136 331 V11.17.0 (2017-02)
AntennaInfoDedicated-v10i0::= SEQUENCE {
 maxLayersMIMO-r10 ENUMERATED {twoLayers, fourLayers, eightLayers} OPTIONAL -- Need
OR
}
AntennaInfoUL-r10 ::= SEQUENCE {
 transmissionModeUL-r10 ENUMERATED {tm1, tm2, spare6, spare5,
 spare4, spare3, spare2, spare1} OPTIONAL, -- Need OR 
ETSI
3GPP TS 36.331 version 11.17.0 Release 11 236 ETSI TS 136 331 V11.17.0 (2017-02)
 fourAntennaPortActivated-r10 ENUMERATED {setup} OPTIONAL -- Need OR
}
CQI-ReportConfig ::= SEQUENCE {
 cqi-ReportModeAperiodic CQI-ReportModeAperiodic OPTIONAL, -- Need OR
 nomPDSCH-RS-EPRE-Offset INTEGER (-1..6),
 cqi-ReportPeriodic CQI-ReportPeriodic OPTIONAL -- Need ON
}
CQI-ReportConfig-v920 ::= SEQUENCE {
 cqi-Mask-r9 ENUMERATED {setup} OPTIONAL, -- Cond cqi-Setup
 pmi-RI-Report-r9 ENUMERATED {setup} OPTIONAL -- Cond PMIRI
}
CQI-ReportConfig-r10 ::= SEQUENCE {
 cqi-ReportAperiodic-r10 CQI-ReportAperiodic-r10 OPTIONAL, -- Need ON
 nomPDSCH-RS-EPRE-Offset INTEGER (-1..6),
 cqi-ReportPeriodic-r10 CQI-ReportPeriodic-r10 OPTIONAL, -- Need ON
 pmi-RI-Report-r9 ENUMERATED {setup} OPTIONAL, -- Cond PMIRIPCell
 csi-SubframePatternConfig-r10 CHOICE {
 release NULL,
 setup SEQUENCE {
 csi-MeasSubframeSet1-r10 MeasSubframePattern-r10, 
ETSI
3GPP TS 36.331 version 11.17.0 Release 11 237 ETSI TS 136 331 V11.17.0 (2017-02)
 csi-MeasSubframeSet2-r10 MeasSubframePattern-r10
 }
 } OPTIONAL -- Need ON
}
CQI-ReportConfig-v1130 ::= SEQUENCE {
 cqi-ReportPeriodic-v1130 CQI-ReportPeriodic-v1130,
 cqi-ReportBoth-r11 CQI-ReportBoth-r11
}
CQI-ReportConfigSCell-r10 ::= SEQUENCE {
 cqi-ReportModeAperiodic-r10 CQI-ReportModeAperiodic OPTIONAL, -- Need OR
 nomPDSCH-RS-EPRE-Offset-r10 INTEGER (-1..6),
 cqi-ReportPeriodicSCell-r10 CQI-ReportPeriodic-r10 OPTIONAL, -- Need ON
 pmi-RI-Report-r10 ENUMERATED {setup} OPTIONAL -- Cond PMIRISCell
}
CQI-ReportPeriodic ::= CHOICE {
 release NULL,
 setup SEQUENCE {
 cqi-PUCCH-ResourceIndex INTEGER (0..1185),
 cqi-pmi-ConfigIndex INTEGER (0..1023),
 cqi-FormatIndicatorPeriodic CHOICE {
 widebandCQI NULL,
 subbandCQI SEQUENCE {
 k INTEGER (1..4)
 }
 },
 ri-ConfigIndex INTEGER (0..1023) OPTIONAL, -- Need OR
 simultaneousAckNackAndCQI BOOLEAN
 }
}
CQI-ReportPeriodic-r10 ::= CHOICE {
 release NULL, 
ETSI
3GPP TS 36.331 version 11.17.0 Release 11 238 ETSI TS 136 331 V11.17.0 (2017-02)
 setup SEQUENCE {
 cqi-PUCCH-ResourceIndex-r10 INTEGER (0..1184),
 cqi-PUCCH-ResourceIndexP1-r10 INTEGER (0..1184) OPTIONAL, -- Need OR
 cqi-pmi-ConfigIndex INTEGER (0..1023),
 cqi-FormatIndicatorPeriodic-r10 CHOICE {
 widebandCQI-r10 SEQUENCE {
 csi-ReportMode-r10 ENUMERATED {submode1, submode2} OPTIONAL -- Need OR
 },
 subbandCQI-r10 SEQUENCE {
 k INTEGER (1..4),
 periodicityFactor-r10 ENUMERATED {n2, n4}
 }
 },
 ri-ConfigIndex INTEGER (0..1023) OPTIONAL, -- Need OR
 simultaneousAckNackAndCQI BOOLEAN,
 cqi-Mask-r9 ENUMERATED {setup} OPTIONAL, -- Need OR
 csi-ConfigIndex-r10 CHOICE {
 release NULL,
 setup SEQUENCE {
 cqi-pmi-ConfigIndex2-r10 INTEGER (0..1023),
 ri-ConfigIndex2-r10 INTEGER (0..1023) OPTIONAL -- Need OR
 }
 } OPTIONAL -- Need ON
 }
}
CQI-ReportPeriodic-v1130 ::= SEQUENCE {
 simultaneousAckNackAndCQI-Format3-r11 ENUMERATED {setup} OPTIONAL, -- Need OR
 cqi-ReportPeriodicProcExtToReleaseList-r11 CQI-ReportPeriodicProcExtToReleaseList-r11 OPTIONAL, --
Need ON
 cqi-ReportPeriodicProcExtToAddModList-r11 CQI-ReportPeriodicProcExtToAddModList-r11 OPTIONAL --
Need ON
}
CQI-ReportPeriodicProcExtToAddModList-r11 ::= SEQUENCE (SIZE (1..maxCQI-ProcExt-r11)) OF CQIReportPeriodicProcExt-r11

ETSI
3GPP TS 36.331 version 11.17.0 Release 11 239 ETSI TS 136 331 V11.17.0 (2017-02)
CQI-ReportPeriodicProcExtToReleaseList-r11 ::= SEQUENCE (SIZE (1..maxCQI-ProcExt-r11)) OF CQIReportPeriodicProcExtId-r11

CQI-ReportPeriodicProcExt-r11 ::= SEQUENCE {
 cqi-ReportPeriodicProcExtId-r11 CQI-ReportPeriodicProcExtId-r11,
 cqi-pmi-ConfigIndex-r11 INTEGER (0..1023),
 cqi-FormatIndicatorPeriodic-r11 CHOICE {
 widebandCQI-r11 SEQUENCE {
 csi-ReportMode-r11 ENUMERATED {submode1, submode2} OPTIONAL -- Need OR
 },
 subbandCQI-r11 SEQUENCE {
 k INTEGER (1..4),
 periodicityFactor-r11 ENUMERATED {n2, n4}
 }
 },
 ri-ConfigIndex-r11 INTEGER (0..1023) OPTIONAL, -- Need OR
 csi-ConfigIndex-r11 CHOICE {
 release NULL,
 setup SEQUENCE {
 cqi-pmi-ConfigIndex2-r11 INTEGER (0..1023),
 ri-ConfigIndex2-r11 INTEGER (0..1023) OPTIONAL -- Need OR
 }
 } OPTIONAL, -- Need ON
 ...
}
CQI-ReportAperiodic-r10 ::= CHOICE {
 release NULL,
 setup SEQUENCE {
 cqi-ReportModeAperiodic-r10 CQI-ReportModeAperiodic,
 aperiodicCSI-Trigger-r10 SEQUENCE {
 trigger1-r10 BIT STRING (SIZE (8)),
 trigger2-r10 BIT STRING (SIZE (8))
 } OPTIONAL -- Need OR 
ETSI
3GPP TS 36.331 version 11.17.0 Release 11 240 ETSI TS 136 331 V11.17.0 (2017-02)
 }
}
CQI-ReportAperiodicProc-r11 ::= SEQUENCE {
 cqi-ReportModeAperiodic-r11 CQI-ReportModeAperiodic,
 trigger01-r11 BOOLEAN,
 trigger10-r11 BOOLEAN,
 trigger11-r11 BOOLEAN
}
CQI-ReportModeAperiodic ::= ENUMERATED {
 rm12, rm20, rm22, rm30, rm31,
 spare3, spare2, spare1
}
CQI-ReportBoth-r11 ::= SEQUENCE {
 csi-IM-ConfigToReleaseList-r11 CSI-IM-ConfigToReleaseList-r11 OPTIONAL, -- Need ON
 csi-IM-ConfigToAddModList-r11 CSI-IM-ConfigToAddModList-r11 OPTIONAL, -- Need ON
 csi-ProcessToReleaseList-r11 CSI-ProcessToReleaseList-r11 OPTIONAL, -- Need ON
 csi-ProcessToAddModList-r11 CSI-ProcessToAddModList-r11 OPTIONAL -- Need ON
}
CSI-IM-ConfigToAddModList-r11 ::= SEQUENCE (SIZE (1..maxCSI-IM-r11)) OF CSI-IM-Config-r11
CSI-IM-ConfigToReleaseList-r11 ::= SEQUENCE (SIZE (1..maxCSI-IM-r11)) OF CSI-IM-ConfigId-r11
CSI-ProcessToAddModList-r11 ::= SEQUENCE (SIZE (1..maxCSI-Proc-r11)) OF CSI-Process-r11
CSI-ProcessToReleaseList-r11 ::= SEQUENCE (SIZE (1..maxCSI-Proc-r11)) OF CSI-ProcessId-r11
CQI-ReportBothProc-r11 ::= SEQUENCE {
 ri-Ref-CSI-ProcessId-r11 CSI-ProcessId-r11 OPTIONAL, -- Need OR
 pmi-RI-Report-r11 ENUMERATED {setup} OPTIONAL -- Need OR
} 
ETSI
3GPP TS 36.331 version 11.17.0 Release 11 241 ETSI TS 136 331 V11.17.0 (2017-02)
CQI-ReportPeriodicProcExtId-r11 ::= INTEGER (1..maxCQI-ProcExt-r11) 
ETSI
3GPP TS 36.331 version 11.17.0 Release 11 244 ETSI TS 136 331 V11.17.0 (2017-02)
CrossCarrierSchedulingConfig-r10 ::= SEQUENCE {
 schedulingCellInfo-r10 CHOICE {
 own-r10 SEQUENCE { -- No cross carrier scheduling
 cif-Presence-r10 BOOLEAN
 },
 other-r10 SEQUENCE { -- Cross carrier scheduling
 schedulingCellId-r10 ServCellIndex-r10,
 pdsch-Start-r10 INTEGER (1..4)
 }
 }
}
ETSI
3GPP TS 36.331 version 11.17.0 Release 11 245 ETSI TS 136 331 V11.17.0 (2017-02)
CSI-IM-Config-r11 ::= SEQUENCE {
 csi-IM-ConfigId-r11 CSI-IM-ConfigId-r11,
 resourceConfig-r11 INTEGER (0..31),
 subframeConfig-r11 INTEGER (0..154),
 ...
}
CSI-IM-ConfigId-r11 ::= INTEGER (1..maxCSI-IM-r11)
CSI-Process-r11 ::= SEQUENCE {
 csi-ProcessId-r11 CSI-ProcessId-r11,
 csi-RS-ConfigNZPId-r11 CSI-RS-ConfigNZPId-r11,
 csi-IM-ConfigId-r11 CSI-IM-ConfigId-r11,
 p-C-AndCBSRList-r11 SEQUENCE (SIZE (1..2)) OF P-C-AndCBSR-r11, 
ETSI
3GPP TS 36.331 version 11.17.0 Release 11 246 ETSI TS 136 331 V11.17.0 (2017-02)
 cqi-ReportBothProc-r11 CQI-ReportBothProc-r11 OPTIONAL, -- Need OR
 cqi-ReportPeriodicProcId-r11 INTEGER (0..maxCQI-ProcExt-r11) OPTIONAL, -- Need OR
 cqi-ReportAperiodicProc-r11 CQI-ReportAperiodicProc-r11 OPTIONAL, -- Need OR
 ...
}
P-C-AndCBSR-r11 ::= SEQUENCE {
 p-C-r11 INTEGER (-8..15),
 codebookSubsetRestriction-r11 BIT STRING
}
CSI-ProcessId-r11 ::= INTEGER (1..maxCSI-Proc-r11)
CSI-RS-Config-r10 ::= SEQUENCE {
 csi-RS-r10 CHOICE {
 release NULL,
 setup SEQUENCE {
 antennaPortsCount-r10 ENUMERATED {an1, an2, an4, an8},
 resourceConfig-r10 INTEGER (0..31),
 subframeConfig-r10 INTEGER (0..154),
 p-C-r10 INTEGER (-8..15)
 }
 } OPTIONAL, -- Need ON
 zeroTxPowerCSI-RS-r10 CHOICE {
 release NULL,
 setup SEQUENCE {
 zeroTxPowerResourceConfigList-r10 BIT STRING (SIZE (16)),
 zeroTxPowerSubframeConfig-r10 INTEGER (0..154)
 }
 } OPTIONAL -- Need ON
}
CSI-RS-ConfigNZP-r11 ::= SEQUENCE {
 csi-RS-ConfigNZPId-r11 CSI-RS-ConfigNZPId-r11,
 antennaPortsCount-r11 ENUMERATED {an1, an2, an4, an8},
 resourceConfig-r11 INTEGER (0..31),
 subframeConfig-r11 INTEGER (0..154),
 scramblingIdentity-r11 INTEGER (0..503),
 qcl-CRS-Info-r11 SEQUENCE {
 qcl-ScramblingIdentity-r11 INTEGER (0..503),
 crs-PortsCount-r11 ENUMERATED {n1, n2, n4, spare1},
 mbsfn-SubframeConfigList-r11 CHOICE {
 release NULL,
 setup SEQUENCE {
 subframeConfigList MBSFN-SubframeConfigList
 }
 } OPTIONAL -- Need ON
 } OPTIONAL, -- Need OR
 ...
}
CSI-RS-ConfigNZPId-r11 ::= INTEGER (1..maxCSI-RS-NZP-r11)
CSI-RS-ConfigZP-r11 ::= SEQUENCE {
 csi-RS-ConfigZPId-r11 CSI-RS-ConfigZPId-r11,
 resourceConfigList-r11 BIT STRING (SIZE (16)),
 subframeConfig-r11 INTEGER (0..154),
 ...
}
CSI-RS-ConfigZPId-r11 ::= INTEGER (1..maxCSI-RS-ZP-r11)
DMRS-Config-r11 ::= CHOICE {
 release NULL,
 setup SEQUENCE {
 scramblingIdentity-r11 INTEGER (0..503),
 scramblingIdentity2-r11 INTEGER (0..503)
 }
}
DRB-Identity ::= INTEGER (1..32)
EPDCCH-Config-r11 ::= SEQUENCE{
 config-r11 CHOICE {
 release NULL,
 setup SEQUENCE {
 subframePatternConfig-r11 CHOICE {
 release NULL,
 setup SEQUENCE {
 subframePattern-r11 MeasSubframePattern-r10
 }
 } OPTIONAL, -- Need ON
 startSymbol-r11 INTEGER (1..4) OPTIONAL, -- Need OP
 setConfigToReleaseList-r11 EPDCCH-SetConfigToReleaseList-r11 OPTIONAL, -- Need ON
 setConfigToAddModList-r11 EPDCCH-SetConfigToAddModList-r11 OPTIONAL -- Need ON
 }
 }
}
EPDCCH-SetConfigToAddModList-r11 ::= SEQUENCE (SIZE(1..maxEPDCCH-Set-r11)) OF EPDCCH-SetConfigr11

ETSI
3GPP TS 36.331 version 11.17.0 Release 11 252 ETSI TS 136 331 V11.17.0 (2017-02)
EPDCCH-SetConfigToReleaseList-r11 ::= SEQUENCE (SIZE(1..maxEPDCCH-Set-r11)) OF EPDCCHSetConfigId-r11

EPDCCH-SetConfig-r11 ::= SEQUENCE {
 setConfigId-r11 EPDCCH-SetConfigId-r11,
 transmissionType-r11 ENUMERATED {localised, distributed},
 resourceBlockAssignment-r11 SEQUENCE{
 numberPRB-Pairs-r11 ENUMERATED {n2, n4, n8},
 resourceBlockAssignment-r11 BIT STRING (SIZE(4..38))
 },
 dmrs-ScramblingSequenceInt-r11 INTEGER (0..503),
 pucch-ResourceStartOffset-r11 INTEGER (0..2047),
 re-MappingQCL-ConfigId-r11 PDSCH-RE-MappingQCL-ConfigId-r11 OPTIONAL, -- Need OR
 ...
}
EPDCCH-SetConfigId-r11 ::= INTEGER (0..1)
LogicalChannelConfig ::= SEQUENCE {
 ul-SpecificParameters SEQUENCE {
 priority INTEGER (1..16),
 prioritisedBitRate ENUMERATED {
 kBps0, kBps8, kBps16, kBps32, kBps64, kBps128,
 kBps256, infinity, kBps512-v1020, kBps1024-v1020,
 kBps2048-v1020, spare5, spare4, spare3, spare2,
 spare1},
 bucketSizeDuration ENUMERATED {
 ms50, ms100, ms150, ms300, ms500, ms1000, spare2, 
ETSI
3GPP TS 36.331 version 11.17.0 Release 11 254 ETSI TS 136 331 V11.17.0 (2017-02)
 spare1},
 logicalChannelGroup INTEGER (0..3) OPTIONAL -- Need OR
 } OPTIONAL, -- Cond UL
 ...,
 [[ logicalChannelSR-Mask-r9 ENUMERATED {setup} OPTIONAL -- Cond SRmask
 ]]
}
MAC-MainConfig ::= SEQUENCE {
 ul-SCH-Config SEQUENCE {
 maxHARQ-Tx ENUMERATED {
 n1, n2, n3, n4, n5, n6, n7, n8,
 n10, n12, n16, n20, n24, n28,
 spare2, spare1} OPTIONAL, -- Need ON
 periodicBSR-Timer ENUMERATED {
 sf5, sf10, sf16, sf20, sf32, sf40, sf64, sf80, 
ETSI
3GPP TS 36.331 version 11.17.0 Release 11 255 ETSI TS 136 331 V11.17.0 (2017-02)
 sf128, sf160, sf320, sf640, sf1280, sf2560,
 infinity, spare1} OPTIONAL, -- Need ON
 retxBSR-Timer ENUMERATED {
 sf320, sf640, sf1280, sf2560, sf5120,
 sf10240, spare2, spare1},
 ttiBundling BOOLEAN
 } OPTIONAL, -- Need ON
 drx-Config DRX-Config OPTIONAL, -- Need ON
 timeAlignmentTimerDedicated TimeAlignmentTimer,
 phr-Config CHOICE {
 release NULL,
 setup SEQUENCE {
 periodicPHR-Timer ENUMERATED {sf10, sf20, sf50, sf100, sf200,
 sf500, sf1000, infinity},
 prohibitPHR-Timer ENUMERATED {sf0, sf10, sf20, sf50, sf100,
 sf200, sf500, sf1000},
 dl-PathlossChange ENUMERATED {dB1, dB3, dB6, infinity}
 }
 } OPTIONAL, -- Need ON
 ...,
 [[ sr-ProhibitTimer-r9 INTEGER (0..7) OPTIONAL -- Need ON
 ]],
 [[ mac-MainConfig-v1020 SEQUENCE {
 sCellDeactivationTimer-r10 ENUMERATED {
 rf2, rf4, rf8, rf16, rf32, rf64, rf128,
 spare} OPTIONAL, -- Need OP
 extendedBSR-Sizes-r10 ENUMERATED {setup} OPTIONAL, -- Need OR
 extendedPHR-r10 ENUMERATED {setup} OPTIONAL -- Need OR
 } OPTIONAL -- Need ON
 ]],
 [[ stag-ToReleaseList-r11 STAG-ToReleaseList-r11 OPTIONAL, -- Need ON
 stag-ToAddModList-r11 STAG-ToAddModList-r11 OPTIONAL, -- Need ON
 drx-Config-v1130 DRX-Config-v1130 OPTIONAL -- Need ON
 ]]
} 
ETSI
3GPP TS 36.331 version 11.17.0 Release 11 256 ETSI TS 136 331 V11.17.0 (2017-02)
MAC-MainConfigSCell-r11 ::= SEQUENCE {
 stag-Id-r11 STAG-Id-r11 OPTIONAL, -- Need OP
 ...
}
DRX-Config ::= CHOICE {
 release NULL,
 setup SEQUENCE {
 onDurationTimer ENUMERATED {
 psf1, psf2, psf3, psf4, psf5, psf6,
 psf8, psf10, psf20, psf30, psf40,
 psf50, psf60, psf80, psf100,
 psf200},
 drx-InactivityTimer ENUMERATED {
 psf1, psf2, psf3, psf4, psf5, psf6,
 psf8, psf10, psf20, psf30, psf40,
 psf50, psf60, psf80, psf100,
 psf200, psf300, psf500, psf750,
 psf1280, psf1920, psf2560, psf0-v1020,
 spare9, spare8, spare7, spare6,
 spare5, spare4, spare3, spare2,
 spare1},
 drx-RetransmissionTimer ENUMERATED {
 psf1, psf2, psf4, psf6, psf8, psf16,
 psf24, psf33},
 longDRX-CycleStartOffset CHOICE {
 sf10 INTEGER(0..9),
 sf20 INTEGER(0..19),
 sf32 INTEGER(0..31),
 sf40 INTEGER(0..39),
 sf64 INTEGER(0..63),
 sf80 INTEGER(0..79),
 sf128 INTEGER(0..127),
 sf160 INTEGER(0..159), 
ETSI
3GPP TS 36.331 version 11.17.0 Release 11 257 ETSI TS 136 331 V11.17.0 (2017-02)
 sf256 INTEGER(0..255),
 sf320 INTEGER(0..319),
 sf512 INTEGER(0..511),
 sf640 INTEGER(0..639),
 sf1024 INTEGER(0..1023),
 sf1280 INTEGER(0..1279),
 sf2048 INTEGER(0..2047),
 sf2560 INTEGER(0..2559)
 },
 shortDRX SEQUENCE {
 shortDRX-Cycle ENUMERATED {
 sf2, sf5, sf8, sf10, sf16, sf20,
 sf32, sf40, sf64, sf80, sf128, sf160,
 sf256, sf320, sf512, sf640},
 drxShortCycleTimer INTEGER (1..16)
 } OPTIONAL -- Need OR
 }
}
DRX-Config-v1130 ::= SEQUENCE {
 drx-RetransmissionTimer-v1130 ENUMERATED {psf0-v1130} OPTIONAL, --Need OR
 longDRX-CycleStartOffset-v1130 CHOICE {
 sf60-v1130 INTEGER(0..59),
 sf70-v1130 INTEGER(0..69)
 } OPTIONAL, --Need OR
 shortDRX-Cycle-v1130 ENUMERATED {sf4-v1130} OPTIONAL --Need OR
}
STAG-ToReleaseList-r11 ::= SEQUENCE (SIZE (1..maxSTAG-r11)) OF STAG-Id-r11
STAG-ToAddModList-r11 ::= SEQUENCE (SIZE (1..maxSTAG-r11)) OF STAG-ToAddMod-r11
STAG-ToAddMod-r11 ::= SEQUENCE {
 stag-Id-r11 STAG-Id-r11,
 timeAlignmentTimerSTAG-r11TimeAlignmentTimer, 
ETSI
3GPP TS 36.331 version 11.17.0 Release 11 258 ETSI TS 136 331 V11.17.0 (2017-02)
 ...
}
STAG-Id-r11::= INTEGER (1..maxSTAG-r11)
PDCP-Config ::= SEQUENCE {
 discardTimer ENUMERATED {
 ms50, ms100, ms150, ms300, ms500,
 ms750, ms1500, infinity
 } OPTIONAL, -- Cond Setup
 rlc-AM SEQUENCE {
 statusReportRequired BOOLEAN
 } OPTIONAL, -- Cond Rlc-AM
 rlc-UM SEQUENCE {
 pdcp-SN-Size ENUMERATED {len7bits, len12bits}
 } OPTIONAL, -- Cond Rlc-UM
 headerCompression CHOICE {
 notUsed NULL,
 rohc SEQUENCE {
 maxCID INTEGER (1..16383) DEFAULT 15,
 profiles SEQUENCE {
 profile0x0001 BOOLEAN,
 profile0x0002 BOOLEAN,
 profile0x0003 BOOLEAN,
 profile0x0004 BOOLEAN,
 profile0x0006 BOOLEAN, 
ETSI
3GPP TS 36.331 version 11.17.0 Release 11 261 ETSI TS 136 331 V11.17.0 (2017-02)
 profile0x0101 BOOLEAN,
 profile0x0102 BOOLEAN,
 profile0x0103 BOOLEAN,
 profile0x0104 BOOLEAN
 },
 ...
 }
 },
 ...,
 [[ rn-IntegrityProtection-r10 ENUMERATED {enabled} OPTIONAL -- Cond RN
 ]],
 [[ pdcp-SN-Size-v1130 ENUMERATED {len15bits} OPTIONAL -- Cond Rlc-AM2
 ]]
}
PDSCH-ConfigCommon ::= SEQUENCE {
 referenceSignalPower INTEGER (-60..50),
 p-b INTEGER (0..3)
}
PDSCH-ConfigDedicated::= SEQUENCE {
 p-a ENUMERATED {
 dB-6, dB-4dot77, dB-3, dB-1dot77,
 dB0, dB1, dB2, dB3}
}
PDSCH-ConfigDedicated-v1130 ::= SEQUENCE {
 dmrs-ConfigPDSCH-r11 DMRS-Config-r11 OPTIONAL, -- Need ON
 qcl-Operation ENUMERATED {typeA, typeB} OPTIONAL, -- Need OR
 re-MappingQCLConfigToReleaseList-r11 RE-MappingQCLConfigToReleaseList-r11 OPTIONAL, -- Need ON
 re-MappingQCLConfigToAddModList-r11 RE-MappingQCLConfigToAddModList-r11 OPTIONAL --
Need ON
} 
ETSI
3GPP TS 36.331 version 11.17.0 Release 11 263 ETSI TS 136 331 V11.17.0 (2017-02)
RE-MappingQCLConfigToAddModList-r11 ::= SEQUENCE (SIZE (1..maxRE-MapQCL-r11)) OF PDSCH-REMappingQCL-Config-r11

RE-MappingQCLConfigToReleaseList-r11 ::= SEQUENCE (SIZE (1..maxRE-MapQCL-r11)) OF PDSCH-REMappingQCL-ConfigId-r11

PDSCH-RE-MappingQCL-Config-r11 ::= SEQUENCE {
 pdsch-RE-MappingQCL-ConfigId-r11 PDSCH-RE-MappingQCL-ConfigId-r11,
 optionalSetOfFields-r11 SEQUENCE {
 crs-PortsCount-r11 ENUMERATED {n1, n2, n4, spare1},
 crs-FreqShift-r11 INTEGER (0..5),
 mbsfn-SubframeConfigList-r11 CHOICE {
 release NULL,
 setup SEQUENCE {
 subframeConfigList MBSFN-SubframeConfigList
 }
 } OPTIONAL, -- Need ON
 pdsch-Start-r11 ENUMERATED {reserved, n1, n2, n3, n4, assigned}
 } OPTIONAL, -- Need OP
 csi-RS-ConfigZPId-r11 CSI-RS-ConfigZPId-r11,
 qcl-CSI-RS-ConfigNZPId-r11 CSI-RS-ConfigNZPId-r11 OPTIONAL, -- Need OR
 ...
}
PDSCH-RE-MappingQCL-ConfigId-r11 ::= INTEGER (1..maxRE-MapQCL-r11)
PHICH-Config ::= SEQUENCE {
 phich-Duration ENUMERATED {normal, extended},
 phich-Resource ENUMERATED {oneSixth, half, one, two}
} 
ETSI
3GPP TS 36.331 version 11.17.0 Release 11 265 ETSI TS 136 331 V11.17.0 (2017-02)
PhysicalConfigDedicated ::= SEQUENCE {
 pdsch-ConfigDedicated PDSCH-ConfigDedicated OPTIONAL, -- Need ON
 pucch-ConfigDedicated PUCCH-ConfigDedicated OPTIONAL, -- Need ON
 pusch-ConfigDedicated PUSCH-ConfigDedicated OPTIONAL, -- Need ON
 uplinkPowerControlDedicated UplinkPowerControlDedicated OPTIONAL, -- Need ON
 tpc-PDCCH-ConfigPUCCH TPC-PDCCH-Config OPTIONAL, -- Need ON
 tpc-PDCCH-ConfigPUSCH TPC-PDCCH-Config OPTIONAL, -- Need ON
 cqi-ReportConfig CQI-ReportConfig OPTIONAL, -- Cond CQI-r8
 soundingRS-UL-ConfigDedicated SoundingRS-UL-ConfigDedicated OPTIONAL, -- Need ON
 antennaInfo CHOICE {
 explicitValue AntennaInfoDedicated,
 defaultValue NULL
 } OPTIONAL, -- Cond AI-r8
 schedulingRequestConfig SchedulingRequestConfig OPTIONAL, -- Need ON
 ...,
 [[ cqi-ReportConfig-v920 CQI-ReportConfig-v920 OPTIONAL, -- Cond CQI-r8
 antennaInfo-v920 AntennaInfoDedicated-v920 OPTIONAL -- Cond AI-r8
 ]],
 [[ antennaInfo-r10 CHOICE {
 explicitValue-r10 AntennaInfoDedicated-r10,
 defaultValue NULL
 } OPTIONAL, -- Cond AI-r10
 antennaInfoUL-r10 AntennaInfoUL-r10 OPTIONAL, -- Need ON 
ETSI
3GPP TS 36.331 version 11.17.0 Release 11 266 ETSI TS 136 331 V11.17.0 (2017-02)
 cif-Presence-r10 BOOLEAN OPTIONAL, -- Need ON
 cqi-ReportConfig-r10 CQI-ReportConfig-r10 OPTIONAL, -- Cond CQI-r10
 csi-RS-Config-r10 CSI-RS-Config-r10 OPTIONAL, -- Need ON
 pucch-ConfigDedicated-v1020 PUCCH-ConfigDedicated-v1020 OPTIONAL, -- Need ON
 pusch-ConfigDedicated-v1020 PUSCH-ConfigDedicated-v1020 OPTIONAL, -- Need ON
 schedulingRequestConfig-v1020 SchedulingRequestConfig-v1020 OPTIONAL, -- Need ON
 soundingRS-UL-ConfigDedicated-v1020
 SoundingRS-UL-ConfigDedicated-v1020 OPTIONAL, -- Need ON
 soundingRS-UL-ConfigDedicatedAperiodic-r10
 SoundingRS-UL-ConfigDedicatedAperiodic-r10 OPTIONAL, -- Need ON
 uplinkPowerControlDedicated-v1020 UplinkPowerControlDedicated-v1020 OPTIONAL -- Need ON
 ]],
 [[ additionalSpectrumEmissionCA-r10 CHOICE {
 release NULL,
 setup SEQUENCE {
 additionalSpectrumEmissionPCell-r10 AdditionalSpectrumEmission
 }
 } OPTIONAL -- Need ON
 ]],
 [[ -- DL configuration as well as configuration applicable for DL and UL
 csi-RS-ConfigNZPToReleaseList-r11 CSI-RS-ConfigNZPToReleaseList-r11 OPTIONAL, -- Need ON
 csi-RS-ConfigNZPToAddModList-r11CSI-RS-ConfigNZPToAddModList-r11 OPTIONAL, -- Need ON
 csi-RS-ConfigZPToReleaseList-r11 CSI-RS-ConfigZPToReleaseList-r11 OPTIONAL, -- Need ON
 csi-RS-ConfigZPToAddModList-r11 CSI-RS-ConfigZPToAddModList-r11 OPTIONAL, -- Need ON
 epdcch-Config-r11 EPDCCH-Config-r11 OPTIONAL, -- Need ON
 pdsch-ConfigDedicated-v1130 PDSCH-ConfigDedicated-v1130 OPTIONAL, -- Need ON
 -- UL configuration
 cqi-ReportConfig-v1130 CQI-ReportConfig-v1130 OPTIONAL, -- Need ON
 pucch-ConfigDedicated-v1130 PUCCH-ConfigDedicated-v1130 OPTIONAL, -- Need ON
 pusch-ConfigDedicated-v1130 PUSCH-ConfigDedicated-v1130 OPTIONAL, -- Need ON
 uplinkPowerControlDedicated-v1130 UplinkPowerControlDedicated-v1130 OPTIONAL -- Need ON
 ]]
}
PhysicalConfigDedicatedSCell-r10 ::= SEQUENCE { 
ETSI
3GPP TS 36.331 version 11.17.0 Release 11 267 ETSI TS 136 331 V11.17.0 (2017-02)
 -- DL configuration as well as configuration applicable for DL and UL
 nonUL-Configuration-r10 SEQUENCE {
 antennaInfo-r10 AntennaInfoDedicated-r10 OPTIONAL, -- Need ON
 crossCarrierSchedulingConfig-r10 CrossCarrierSchedulingConfig-r10 OPTIONAL, -- Need ON
 csi-RS-Config-r10 CSI-RS-Config-r10 OPTIONAL, -- Need ON
 pdsch-ConfigDedicated-r10 PDSCH-ConfigDedicated OPTIONAL -- Need ON
 } OPTIONAL, -- Cond SCellAdd
 -- UL configuration
 ul-Configuration-r10 SEQUENCE {
 antennaInfoUL-r10 AntennaInfoUL-r10 OPTIONAL, -- Need ON
 pusch-ConfigDedicatedSCell-r10 PUSCH-ConfigDedicatedSCell-r10 OPTIONAL, -- Need ON
 uplinkPowerControlDedicatedSCell-r10 UplinkPowerControlDedicatedSCell-r10 OPTIONAL, -- Need ON
 cqi-ReportConfigSCell-r10 CQI-ReportConfigSCell-r10 OPTIONAL, -- Need ON
 soundingRS-UL-ConfigDedicated-r10 SoundingRS-UL-ConfigDedicated OPTIONAL, -- Need ON
 soundingRS-UL-ConfigDedicated-v1020
 SoundingRS-UL-ConfigDedicated-v1020 OPTIONAL, -- Need ON
 soundingRS-UL-ConfigDedicatedAperiodic-r10
 SoundingRS-UL-ConfigDedicatedAperiodic-r10 OPTIONAL -- Need ON
 } OPTIONAL, -- Cond CommonUL
 ...,
 [[ -- DL configuration as well as configuration applicable for DL and UL
 csi-RS-ConfigNZPToReleaseList-r11 CSI-RS-ConfigNZPToReleaseList-r11 OPTIONAL, -- Need ON
 csi-RS-ConfigNZPToAddModList-r11CSI-RS-ConfigNZPToAddModList-r11 OPTIONAL, -- Need ON
 csi-RS-ConfigZPToReleaseList-r11 CSI-RS-ConfigZPToReleaseList-r11 OPTIONAL, -- Need ON
 csi-RS-ConfigZPToAddModList-r11 CSI-RS-ConfigZPToAddModList-r11 OPTIONAL, -- Need ON
 epdcch-Config-r11 EPDCCH-Config-r11 OPTIONAL, -- Need ON
 pdsch-ConfigDedicated-v1130 PDSCH-ConfigDedicated-v1130 OPTIONAL, -- Need ON
 -- UL configuration
 cqi-ReportConfig-v1130 CQI-ReportConfig-v1130 OPTIONAL, -- Need ON
 pusch-ConfigDedicated-v1130 PUSCH-ConfigDedicated-v1130 OPTIONAL, -- Need ON
 uplinkPowerControlDedicatedSCell-v1130 UplinkPowerControlDedicated-v1130 OPTIONAL -- Need ON
 ]]
} 
ETSI
3GPP TS 36.331 version 11.17.0 Release 11 268 ETSI TS 136 331 V11.17.0 (2017-02)
CSI-RS-ConfigNZPToAddModList-r11 ::= SEQUENCE (SIZE (1..maxCSI-RS-NZP-r11)) OF CSI-RS-ConfigNZPr11

CSI-RS-ConfigNZPToReleaseList-r11 ::= SEQUENCE (SIZE (1..maxCSI-RS-NZP-r11)) OF CSI-RS-ConfigNZPIdr11

CSI-RS-ConfigZPToAddModList-r11 ::= SEQUENCE (SIZE (1..maxCSI-RS-ZP-r11)) OF CSI-RS-ConfigZP-r11
CSI-RS-ConfigZPToReleaseList-r11 ::= SEQUENCE (SIZE (1..maxCSI-RS-ZP-r11)) OF CSI-RS-ConfigZPId-r11
P-Max ::= INTEGER (-30..33)
PRACH-ConfigSIB ::= SEQUENCE {
 rootSequenceIndex INTEGER (0..837),
 prach-ConfigInfo PRACH-ConfigInfo
} 
ETSI
3GPP TS 36.331 version 11.17.0 Release 11 270 ETSI TS 136 331 V11.17.0 (2017-02)
PRACH-Config ::= SEQUENCE {
 rootSequenceIndex INTEGER (0..837),
 prach-ConfigInfo PRACH-ConfigInfo OPTIONAL -- Need ON
}
PRACH-ConfigSCell-r10 ::= SEQUENCE {
 prach-ConfigIndex-r10 INTEGER (0..63)
}
PRACH-ConfigInfo ::= SEQUENCE {
 prach-ConfigIndex INTEGER (0..63),
 highSpeedFlag BOOLEAN,
 zeroCorrelationZoneConfig INTEGER (0..15),
 prach-FreqOffset INTEGER (0..94)
}
PresenceAntennaPort1 ::= BOOLEAN 
ETSI
3GPP TS 36.331 version 11.17.0 Release 11 271 ETSI TS 136 331 V11.17.0 (2017-02)
PUCCH-ConfigCommon ::= SEQUENCE {
 deltaPUCCH-Shift ENUMERATED {ds1, ds2, ds3},
 nRB-CQI INTEGER (0..98),
 nCS-AN INTEGER (0..7),
 n1PUCCH-AN INTEGER (0..2047)
}
PUCCH-ConfigDedicated ::= SEQUENCE {
 ackNackRepetition CHOICE{
 release NULL,
 setup SEQUENCE {
 repetitionFactor ENUMERATED {n2, n4, n6, spare1},
 n1PUCCH-AN-Rep INTEGER (0..2047)
 }
 },
 tdd-AckNackFeedbackMode ENUMERATED {bundling, multiplexing} OPTIONAL -- Cond TDD
}
PUCCH-ConfigDedicated-v1020 ::= SEQUENCE {
 pucch-Format-r10 CHOICE {
 format3-r10 SEQUENCE {
 n3PUCCH-AN-List-r10 SEQUENCE (SIZE (1..4)) OF INTEGER (0..549) OPTIONAL, -- Need ON
 twoAntennaPortActivatedPUCCH-Format3-r10 CHOICE {
 release NULL,
 setup SEQUENCE {
 n3PUCCH-AN-ListP1-r10 SEQUENCE (SIZE (1..4)) OF INTEGER (0..549)
 } 
ETSI
3GPP TS 36.331 version 11.17.0 Release 11 272 ETSI TS 136 331 V11.17.0 (2017-02)
 } OPTIONAL -- Need ON
 },
 channelSelection-r10 SEQUENCE {
 n1PUCCH-AN-CS-r10 CHOICE {
 release NULL,
 setup SEQUENCE {
 n1PUCCH-AN-CS-List-r10 SEQUENCE (SIZE (1..2)) OF N1PUCCH-AN-CS-r10
 }
 } OPTIONAL -- Need ON
 }
 } OPTIONAL, -- Need OR
 twoAntennaPortActivatedPUCCH-Format1a1b-r10 ENUMERATED {true} OPTIONAL, -- Need OR
 simultaneousPUCCH-PUSCH-r10 ENUMERATED {true} OPTIONAL, -- Need OR
 n1PUCCH-AN-RepP1-r10 INTEGER (0..2047) OPTIONAL -- Need OR
}
PUCCH-ConfigDedicated-v1130 ::= SEQUENCE {
 n1PUCCH-AN-CS-v1130 CHOICE {
 release NULL,
 setup SEQUENCE {
 n1PUCCH-AN-CS-ListP1-r11 SEQUENCE (SIZE (2..4)) OF INTEGER (0..2047)
 }
 } OPTIONAL, -- Need ON
 nPUCCH-Param-r11 CHOICE {
 release NULL,
 setup SEQUENCE {
 nPUCCH-Identity-r11 INTEGER (0..503),
 n1PUCCH-AN-r11 INTEGER (0..2047)
 }
 } OPTIONAL -- Need ON
}
N1PUCCH-AN-CS-r10 ::= SEQUENCE (SIZE (1..4)) OF INTEGER (0..2047)
PUSCH-ConfigCommon ::= SEQUENCE {
 pusch-ConfigBasic SEQUENCE {
 n-SB INTEGER (1..4),
 hoppingMode ENUMERATED {interSubFrame, intraAndInterSubFrame},
 pusch-HoppingOffset INTEGER (0..98),
 enable64QAM BOOLEAN
 },
 ul-ReferenceSignalsPUSCH UL-ReferenceSignalsPUSCH
}
PUSCH-ConfigDedicated ::= SEQUENCE {
 betaOffset-ACK-Index INTEGER (0..15),
 betaOffset-RI-Index INTEGER (0..15),
 betaOffset-CQI-Index INTEGER (0..15)
}
PUSCH-ConfigDedicated-v1020 ::= SEQUENCE {
 betaOffsetMC-r10 SEQUENCE {
 betaOffset-ACK-Index-MC-r10 INTEGER (0..15),
 betaOffset-RI-Index-MC-r10 INTEGER (0..15),
 betaOffset-CQI-Index-MC-r10 INTEGER (0..15)
 } OPTIONAL, -- Need OR
 groupHoppingDisabled-r10 ENUMERATED {true} OPTIONAL, -- Need OR
 dmrs-WithOCC-Activated-r10 ENUMERATED {true} OPTIONAL -- Need OR
}
PUSCH-ConfigDedicated-v1130 ::= SEQUENCE {
 pusch-DMRS-r11 CHOICE { 
ETSI
3GPP TS 36.331 version 11.17.0 Release 11 275 ETSI TS 136 331 V11.17.0 (2017-02)
 release NULL,
 setup SEQUENCE {
 nPUSCH-Identity-r11 INTEGER (0..509),
 nDMRS-CSH-Identity-r11 INTEGER (0..509)
 }
 }
}
PUSCH-ConfigDedicatedSCell-r10 ::= SEQUENCE {
 groupHoppingDisabled-r10 ENUMERATED {true} OPTIONAL, -- Need OR
 dmrs-WithOCC-Activated-r10 ENUMERATED {true} OPTIONAL -- Need OR
}
UL-ReferenceSignalsPUSCH ::= SEQUENCE {
 groupHoppingEnabled BOOLEAN,
 groupAssignmentPUSCH INTEGER (0..29),
 sequenceHoppingEnabled BOOLEAN,
 cyclicShift INTEGER (0..7)
}
RACH-ConfigCommon ::= SEQUENCE {
 preambleInfo SEQUENCE {
 numberOfRA-Preambles ENUMERATED {
 n4, n8, n12, n16 ,n20, n24, n28,
 n32, n36, n40, n44, n48, n52, n56,
 n60, n64}, 
ETSI
3GPP TS 36.331 version 11.17.0 Release 11 277 ETSI TS 136 331 V11.17.0 (2017-02)
 preamblesGroupAConfig SEQUENCE {
 sizeOfRA-PreamblesGroupA ENUMERATED {
 n4, n8, n12, n16 ,n20, n24, n28,
 n32, n36, n40, n44, n48, n52, n56,
 n60},
 messageSizeGroupA ENUMERATED {b56, b144, b208, b256},
 messagePowerOffsetGroupB ENUMERATED {
 minusinfinity, dB0, dB5, dB8, dB10, dB12,
 dB15, dB18},
 ...
 } OPTIONAL -- Need OP
 },
 powerRampingParameters PowerRampingParameters,
 ra-SupervisionInfo SEQUENCE {
 preambleTransMax PreambleTransMax,
 ra-ResponseWindowSize ENUMERATED {
 sf2, sf3, sf4, sf5, sf6, sf7,
 sf8, sf10},
 mac-ContentionResolutionTimer ENUMERATED {
 sf8, sf16, sf24, sf32, sf40, sf48,
 sf56, sf64}
 },
 maxHARQ-Msg3Tx INTEGER (1..8),
 ...
}
RACH-ConfigCommonSCell-r11 ::= SEQUENCE {
 powerRampingParameters-r11 PowerRampingParameters,
 ra-SupervisionInfo-r11 SEQUENCE {
 preambleTransMax-r11 PreambleTransMax
 },
 ...
}
PowerRampingParameters ::= SEQUENCE { 
ETSI
3GPP TS 36.331 version 11.17.0 Release 11 278 ETSI TS 136 331 V11.17.0 (2017-02)
 powerRampingStep ENUMERATED {dB0, dB2,dB4, dB6},
 preambleInitialReceivedTargetPower ENUMERATED {
 dBm-120, dBm-118, dBm-116, dBm-114, dBm-112,
 dBm-110, dBm-108, dBm-106, dBm-104, dBm-102,
 dBm-100, dBm-98, dBm-96, dBm-94,
 dBm-92, dBm-90}
}
PreambleTransMax ::= ENUMERATED {
 n3, n4, n5, n6, n7, n8, n10, n20, n50,
 n100, n200}
RACH-ConfigDedicated ::= SEQUENCE {
 ra-PreambleIndex INTEGER (0..63),
 ra-PRACH-MaskIndex INTEGER (0..15)
}
RadioResourceConfigCommonSIB ::= SEQUENCE {
 rach-ConfigCommon RACH-ConfigCommon,
 bcch-Config BCCH-Config,
 pcch-Config PCCH-Config,
 prach-Config PRACH-ConfigSIB,
 pdsch-ConfigCommon PDSCH-ConfigCommon,
 pusch-ConfigCommon PUSCH-ConfigCommon,
 pucch-ConfigCommon PUCCH-ConfigCommon,
 soundingRS-UL-ConfigCommon SoundingRS-UL-ConfigCommon,
 uplinkPowerControlCommon UplinkPowerControlCommon,
 ul-CyclicPrefixLength UL-CyclicPrefixLength,
 ..., 
ETSI
3GPP TS 36.331 version 11.17.0 Release 11 280 ETSI TS 136 331 V11.17.0 (2017-02)
 [[ uplinkPowerControlCommon-v1020 UplinkPowerControlCommon-v1020 OPTIONAL -- Need OR
 ]]
}
RadioResourceConfigCommon ::= SEQUENCE {
 rach-ConfigCommon RACH-ConfigCommon OPTIONAL, -- Need ON
 prach-Config PRACH-Config,
 pdsch-ConfigCommon PDSCH-ConfigCommon OPTIONAL, -- Need ON
 pusch-ConfigCommon PUSCH-ConfigCommon,
 phich-Config PHICH-Config OPTIONAL, -- Need ON
 pucch-ConfigCommon PUCCH-ConfigCommon OPTIONAL, -- Need ON
 soundingRS-UL-ConfigCommon SoundingRS-UL-ConfigCommon OPTIONAL, -- Need ON
 uplinkPowerControlCommon UplinkPowerControlCommon OPTIONAL, -- Need ON
 antennaInfoCommon AntennaInfoCommon OPTIONAL, -- Need ON
 p-Max P-Max OPTIONAL, -- Need OP
 tdd-Config TDD-Config OPTIONAL, -- Cond TDD
 ul-CyclicPrefixLength UL-CyclicPrefixLength,
 ...,
 [[ uplinkPowerControlCommon-v1020 UplinkPowerControlCommon-v1020 OPTIONAL -- Need ON
 ]],
 [[ tdd-Config-v1130 TDD-Config-v1130 OPTIONAL -- Cond TDD3
 ]]
}
RadioResourceConfigCommonSCell-r10 ::= SEQUENCE {
 -- DL configuration as well as configuration applicable for DL and UL
 nonUL-Configuration-r10 SEQUENCE {
 -- 1: Cell characteristics
 dl-Bandwidth-r10 ENUMERATED {n6, n15, n25, n50, n75, n100},
 -- 2: Physical configuration, general
 antennaInfoCommon-r10 AntennaInfoCommon,
 mbsfn-SubframeConfigList-r10 MBSFN-SubframeConfigList OPTIONAL, -- Need OR
 -- 3: Physical configuration, control
 phich-Config-r10 PHICH-Config,
 -- 4: Physical configuration, physical channels 
ETSI
3GPP TS 36.331 version 11.17.0 Release 11 281 ETSI TS 136 331 V11.17.0 (2017-02)
 pdsch-ConfigCommon-r10 PDSCH-ConfigCommon,
 tdd-Config-r10 TDD-Config OPTIONAL -- Cond TDDSCell
 },
 -- UL configuration
 ul-Configuration-r10 SEQUENCE {
 ul-FreqInfo-r10 SEQUENCE {
 ul-CarrierFreq-r10 ARFCN-ValueEUTRA OPTIONAL, -- Need OP
 ul-Bandwidth-r10 ENUMERATED {n6, n15,
 n25, n50, n75, n100} OPTIONAL, -- Need OP
 additionalSpectrumEmissionSCell-r10 AdditionalSpectrumEmission
 },
 p-Max-r10 P-Max OPTIONAL, -- Need OP
 uplinkPowerControlCommonSCell-r10 UplinkPowerControlCommonSCell-r10,
 -- A special version of IE UplinkPowerControlCommon may be introduced
 -- 3: Physical configuration, control
 soundingRS-UL-ConfigCommon-r10 SoundingRS-UL-ConfigCommon,
 ul-CyclicPrefixLength-r10 UL-CyclicPrefixLength,
 -- 4: Physical configuration, physical channels
 prach-ConfigSCell-r10 PRACH-ConfigSCell-r10 OPTIONAL, -- Cond TDD-OR-NoR11
 pusch-ConfigCommon-r10 PUSCH-ConfigCommon
 } OPTIONAL, -- Need OR
 ...,
 [[ ul-CarrierFreq-v1090 ARFCN-ValueEUTRA-v9e0 OPTIONAL -- Need OP
 ]],
 [[ rach-ConfigCommonSCell-r11 RACH-ConfigCommonSCell-r11 OPTIONAL, -- Cond UL
 prach-ConfigSCell-r11 PRACH-Config OPTIONAL, -- Cond UL
 tdd-Config-v1130 TDD-Config-v1130 OPTIONAL, -- Cond TDD2
 uplinkPowerControlCommonSCell-v1130
 UplinkPowerControlCommonSCell-v1130 OPTIONAL -- Cond UL
 ]]
}
BCCH-Config ::= SEQUENCE {
 modificationPeriodCoeff ENUMERATED {n2, n4, n8, n16}
} 
ETSI
3GPP TS 36.331 version 11.17.0 Release 11 282 ETSI TS 136 331 V11.17.0 (2017-02)
PCCH-Config ::= SEQUENCE {
 defaultPagingCycle ENUMERATED {
 rf32, rf64, rf128, rf256},
 nB ENUMERATED {
 fourT, twoT, oneT, halfT, quarterT, oneEighthT,
 oneSixteenthT, oneThirtySecondT}
}
UL-CyclicPrefixLength ::= ENUMERATED {len1, len2}
RadioResourceConfigDedicated ::= SEQUENCE {
 srb-ToAddModList SRB-ToAddModList OPTIONAL, -- Cond HO-Conn
 drb-ToAddModList DRB-ToAddModList OPTIONAL, -- Cond HO-toEUTRA
 drb-ToReleaseList DRB-ToReleaseList OPTIONAL, -- Need ON
 mac-MainConfig CHOICE {
 explicitValue MAC-MainConfig,
 defaultValue NULL
 } OPTIONAL, -- Cond HO-toEUTRA2
 sps-Config SPS-Config OPTIONAL, -- Need ON
 physicalConfigDedicated PhysicalConfigDedicated OPTIONAL, -- Need ON
 ...,
 [[ rlf-TimersAndConstants-r9 RLF-TimersAndConstants-r9 OPTIONAL -- Need ON
 ]],
 [[ measSubframePatternPCell-r10 MeasSubframePatternPCell-r10 OPTIONAL -- Need ON
 ]],
 [[ neighCellsCRS-Info-r11 NeighCellsCRS-Info-r11 OPTIONAL -- Need ON
 ]]
}
RadioResourceConfigDedicatedSCell-r10 ::= SEQUENCE { 
ETSI
3GPP TS 36.331 version 11.17.0 Release 11 284 ETSI TS 136 331 V11.17.0 (2017-02)
 -- UE specific configuration extensions applicable for an SCell
 physicalConfigDedicatedSCell-r10 PhysicalConfigDedicatedSCell-r10 OPTIONAL, -- Need ON
 ...,
 [[ mac-MainConfigSCell-r11 MAC-MainConfigSCell-r11 OPTIONAL -- Cond SCellAdd
 ]]
}
SRB-ToAddModList ::= SEQUENCE (SIZE (1..2)) OF SRB-ToAddMod
SRB-ToAddMod ::= SEQUENCE {
 srb-Identity INTEGER (1..2),
 rlc-Config CHOICE {
 explicitValue RLC-Config,
 defaultValue NULL
 } OPTIONAL, -- Cond Setup
 logicalChannelConfig CHOICE {
 explicitValue LogicalChannelConfig,
 defaultValue NULL
 } OPTIONAL, -- Cond Setup
 ...
}
DRB-ToAddModList ::= SEQUENCE (SIZE (1..maxDRB)) OF DRB-ToAddMod
DRB-ToAddMod ::= SEQUENCE {
 eps-BearerIdentity INTEGER (0..15) OPTIONAL, -- Cond DRB-Setup
 drb-Identity DRB-Identity,
 pdcp-Config PDCP-Config OPTIONAL, -- Cond PDCP
 rlc-Config RLC-Config OPTIONAL, -- Cond Setup
 logicalChannelIdentity INTEGER (3..10) OPTIONAL, -- Cond DRB-Setup
 logicalChannelConfig LogicalChannelConfig OPTIONAL, -- Cond Setup
 ...
}
DRB-ToReleaseList ::= SEQUENCE (SIZE (1..maxDRB)) OF DRB-Identity 
ETSI
3GPP TS 36.331 version 11.17.0 Release 11 285 ETSI TS 136 331 V11.17.0 (2017-02)
MeasSubframePatternPCell-r10 ::= CHOICE {
 release NULL,
 setup MeasSubframePattern-r10
}
NeighCellsCRS-Info-r11 ::= CHOICE {
 release NULL,
 setup CRS-AssistanceInfoList-r11
}
CRS-AssistanceInfoList-r11 ::= SEQUENCE (SIZE (1..maxCellReport)) OF CRS-AssistanceInfo-r11
CRS-AssistanceInfo-r11 ::= SEQUENCE {
 physCellId-r11 PhysCellId,
 antennaPortsCount-r11 ENUMERATED {an1, an2, an4, spare1},
 mbsfn-SubframeConfigList-r11 MBSFN-SubframeConfigList,
 ...
}
ETSI
3GPP TS 36.331 version 11.17.0 Release 11 287 ETSI TS 136 331 V11.17.0 (2017-02)
RLC-Config ::= CHOICE {
 am SEQUENCE {
 ul-AM-RLC UL-AM-RLC,
 dl-AM-RLC DL-AM-RLC
 },
 um-Bi-Directional SEQUENCE {
 ul-UM-RLC UL-UM-RLC,
 dl-UM-RLC DL-UM-RLC
 },
 um-Uni-Directional-UL SEQUENCE {
 ul-UM-RLC UL-UM-RLC
 },
 um-Uni-Directional-DL SEQUENCE {
 dl-UM-RLC DL-UM-RLC
 },
 ...
}
UL-AM-RLC ::= SEQUENCE {
 t-PollRetransmit T-PollRetransmit,
 pollPDU PollPDU,
 pollByte PollByte,
 maxRetxThreshold ENUMERATED {
 t1, t2, t3, t4, t6, t8, t16, t32}
}
DL-AM-RLC ::= SEQUENCE {
 t-Reordering T-Reordering,
 t-StatusProhibit T-StatusProhibit
}
UL-UM-RLC ::= SEQUENCE {
 sn-FieldLength SN-FieldLength
} 
ETSI
3GPP TS 36.331 version 11.17.0 Release 11 288 ETSI TS 136 331 V11.17.0 (2017-02)
DL-UM-RLC ::= SEQUENCE {
 sn-FieldLength SN-FieldLength,
 t-Reordering T-Reordering
}
SN-FieldLength ::= ENUMERATED {size5, size10}
T-PollRetransmit ::= ENUMERATED {
 ms5, ms10, ms15, ms20, ms25, ms30, ms35,
 ms40, ms45, ms50, ms55, ms60, ms65, ms70,
 ms75, ms80, ms85, ms90, ms95, ms100, ms105,
 ms110, ms115, ms120, ms125, ms130, ms135,
 ms140, ms145, ms150, ms155, ms160, ms165,
 ms170, ms175, ms180, ms185, ms190, ms195,
 ms200, ms205, ms210, ms215, ms220, ms225,
 ms230, ms235, ms240, ms245, ms250, ms300,
 ms350, ms400, ms450, ms500, spare9, spare8,
 spare7, spare6, spare5, spare4, spare3,
 spare2, spare1}
PollPDU ::= ENUMERATED {
 p4, p8, p16, p32, p64, p128, p256, pInfinity}
PollByte ::= ENUMERATED {
 kB25, kB50, kB75, kB100, kB125, kB250, kB375,
 kB500, kB750, kB1000, kB1250, kB1500, kB2000,
 kB3000, kBinfinity, spare1}
T-Reordering ::= ENUMERATED {
 ms0, ms5, ms10, ms15, ms20, ms25, ms30, ms35,
 ms40, ms45, ms50, ms55, ms60, ms65, ms70,
 ms75, ms80, ms85, ms90, ms95, ms100, ms110,
 ms120, ms130, ms140, ms150, ms160, ms170,
 ms180, ms190, ms200, spare1} 
ETSI
3GPP TS 36.331 version 11.17.0 Release 11 289 ETSI TS 136 331 V11.17.0 (2017-02)
T-StatusProhibit ::= ENUMERATED {
 ms0, ms5, ms10, ms15, ms20, ms25, ms30, ms35,
 ms40, ms45, ms50, ms55, ms60, ms65, ms70,
 ms75, ms80, ms85, ms90, ms95, ms100, ms105,
 ms110, ms115, ms120, ms125, ms130, ms135,
 ms140, ms145, ms150, ms155, ms160, ms165,
 ms170, ms175, ms180, ms185, ms190, ms195,
 ms200, ms205, ms210, ms215, ms220, ms225,
 ms230, ms235, ms240, ms245, ms250, ms300,
 ms350, ms400, ms450, ms500, spare8, spare7,
 spare6, spare5, spare4, spare3, spare2,
 spare1}
RLF-TimersAndConstants-r9 ::= CHOICE {
 release NULL,
 setup SEQUENCE { 
ETSI
3GPP TS 36.331 version 11.17.0 Release 11 290 ETSI TS 136 331 V11.17.0 (2017-02)
 t301-r9 ENUMERATED {
 ms100, ms200, ms300, ms400, ms600, ms1000, ms1500,
 ms2000},
 t310-r9 ENUMERATED {
 ms0, ms50, ms100, ms200, ms500, ms1000, ms2000},
 n310-r9 ENUMERATED {
 n1, n2, n3, n4, n6, n8, n10, n20},
 t311-r9 ENUMERATED {
 ms1000, ms3000, ms5000, ms10000, ms15000,
 ms20000, ms30000},
 n311-r9 ENUMERATED {
 n1, n2, n3, n4, n5, n6, n8, n10},
 ...
 }
}
RN-SubframeConfig-r10 ::= SEQUENCE {
 subframeConfigPattern-r10 CHOICE {
 subframeConfigPatternFDD-r10 BIT STRING (SIZE(8)),
 subframeConfigPatternTDD-r10 INTEGER (0..31)
 } OPTIONAL, -- Need ON
 rpdcch-Config-r10 SEQUENCE {
 resourceAllocationType-r10 ENUMERATED {type0, type1, type2Localized, type2Distributed,
 spare4, spare3, spare2, spare1}, 
ETSI
3GPP TS 36.331 version 11.17.0 Release 11 291 ETSI TS 136 331 V11.17.0 (2017-02)
 resourceBlockAssignment-r10 CHOICE {
 type01-r10 CHOICE {
 nrb6-r10 BIT STRING (SIZE(6)),
 nrb15-r10 BIT STRING (SIZE(8)),
 nrb25-r10 BIT STRING (SIZE(13)),
 nrb50-r10 BIT STRING (SIZE(17)),
 nrb75-r10 BIT STRING (SIZE(19)),
 nrb100-r10 BIT STRING (SIZE(25))
 },
 type2-r10 CHOICE {
 nrb6-r10 BIT STRING (SIZE(5)),
 nrb15-r10 BIT STRING (SIZE(7)),
 nrb25-r10 BIT STRING (SIZE(9)),
 nrb50-r10 BIT STRING (SIZE(11)),
 nrb75-r10 BIT STRING (SIZE(12)),
 nrb100-r10 BIT STRING (SIZE(13))
 },
 ...
 },
 demodulationRS-r10 CHOICE {
 interleaving-r10 ENUMERATED {crs},
 noInterleaving-r10 ENUMERATED {crs, dmrs}
 },
 pdsch-Start-r10 INTEGER (1..3),
 pucch-Config-r10 CHOICE {
 tdd CHOICE {
 channelSelectionMultiplexingBundling SEQUENCE {
 n1PUCCH-AN-List-r10 SEQUENCE (SIZE (1..4)) OF INTEGER (0..2047)
 },
 fallbackForFormat3 SEQUENCE {
 n1PUCCH-AN-P0-r10 INTEGER (0..2047),
 n1PUCCH-AN-P1-r10 INTEGER (0..2047) OPTIONAL -- Need OR
 }
 },
 fdd SEQUENCE { 
ETSI
3GPP TS 36.331 version 11.17.0 Release 11 292 ETSI TS 136 331 V11.17.0 (2017-02)
 n1PUCCH-AN-P0-r10 INTEGER (0..2047),
 n1PUCCH-AN-P1-r10 INTEGER (0..2047) OPTIONAL -- Need OR
 }
 },
 ...
 } OPTIONAL, -- Need ON
 ...
}
ETSI
3GPP TS 36.331 version 11.17.0 Release 11 293 ETSI TS 136 331 V11.17.0 (2017-02)
SchedulingRequestConfig ::= CHOICE {
 release NULL,
 setup SEQUENCE {
 sr-PUCCH-ResourceIndex INTEGER (0..2047),
 sr-ConfigIndex INTEGER (0..157),
 dsr-TransMax ENUMERATED {
 n4, n8, n16, n32, n64, spare3, spare2, spare1}
 }
}
SchedulingRequestConfig-v1020 ::= SEQUENCE {
 sr-PUCCH-ResourceIndexP1-r10 INTEGER (0..2047) OPTIONAL -- Need OR
}
SoundingRS-UL-ConfigCommon ::= CHOICE {
 release NULL,
 setup SEQUENCE {
 srs-BandwidthConfig ENUMERATED {bw0, bw1, bw2, bw3, bw4, bw5, bw6, bw7},
 srs-SubframeConfig ENUMERATED {
 sc0, sc1, sc2, sc3, sc4, sc5, sc6, sc7, 
ETSI
3GPP TS 36.331 version 11.17.0 Release 11 294 ETSI TS 136 331 V11.17.0 (2017-02)
 sc8, sc9, sc10, sc11, sc12, sc13, sc14, sc15},
 ackNackSRS-SimultaneousTransmission BOOLEAN,
 srs-MaxUpPts ENUMERATED {true} OPTIONAL -- Cond TDD
 }
}
SoundingRS-UL-ConfigDedicated ::= CHOICE{
 release NULL,
 setup SEQUENCE {
 srs-Bandwidth ENUMERATED {bw0, bw1, bw2, bw3},
 srs-HoppingBandwidth ENUMERATED {hbw0, hbw1, hbw2, hbw3},
 freqDomainPosition INTEGER (0..23),
 duration BOOLEAN,
 srs-ConfigIndex INTEGER (0..1023),
 transmissionComb INTEGER (0..1),
 cyclicShift ENUMERATED {cs0, cs1, cs2, cs3, cs4, cs5, cs6, cs7}
 }
}
SoundingRS-UL-ConfigDedicated-v1020 ::= SEQUENCE {
 srs-AntennaPort-r10 SRS-AntennaPort
}
SoundingRS-UL-ConfigDedicatedAperiodic-r10 ::= CHOICE{
 release NULL,
 setup SEQUENCE {
 srs-ConfigIndexAp-r10 INTEGER (0..31),
 srs-ConfigApDCI-Format4-r10 SEQUENCE (SIZE (1..3)) OF SRS-ConfigAp-r10 OPTIONAL,--Need
ON
 srs-ActivateAp-r10 CHOICE {
 release NULL,
 setup SEQUENCE {
 srs-ConfigApDCI-Format0-r10 SRS-ConfigAp-r10,
 srs-ConfigApDCI-Format1a2b2c-r10 SRS-ConfigAp-r10,
 ... 
ETSI
3GPP TS 36.331 version 11.17.0 Release 11 295 ETSI TS 136 331 V11.17.0 (2017-02)
 }
 } OPTIONAL -- Need ON
 }
}
SRS-ConfigAp-r10 ::= SEQUENCE {
 srs-AntennaPortAp-r10 SRS-AntennaPort,
 srs-BandwidthAp-r10 ENUMERATED {bw0, bw1, bw2, bw3},
 freqDomainPositionAp-r10 INTEGER (0..23),
 transmissionCombAp-r10 INTEGER (0..1),
 cyclicShiftAp-r10 ENUMERATED {cs0, cs1, cs2, cs3, cs4, cs5, cs6, cs7}
}
SRS-AntennaPort ::= ENUMERATED {an1, an2, an4, spare1}
SPS-Config ::= SEQUENCE {
 semiPersistSchedC-RNTI C-RNTI OPTIONAL, -- Need OR 
ETSI
3GPP TS 36.331 version 11.17.0 Release 11 297 ETSI TS 136 331 V11.17.0 (2017-02)
 sps-ConfigDL SPS-ConfigDL OPTIONAL, -- Need ON
 sps-ConfigUL SPS-ConfigUL OPTIONAL -- Need ON
}
SPS-ConfigDL ::= CHOICE{
 release NULL,
 setup SEQUENCE {
 semiPersistSchedIntervalDL ENUMERATED {
 sf10, sf20, sf32, sf40, sf64, sf80,
 sf128, sf160, sf320, sf640, spare6,
 spare5, spare4, spare3, spare2,
 spare1},
 numberOfConfSPS-Processes INTEGER (1..8),
 n1PUCCH-AN-PersistentList N1PUCCH-AN-PersistentList,
 ...,
 [[ twoAntennaPortActivated-r10 CHOICE {
 release NULL,
 setup SEQUENCE {
 n1PUCCH-AN-PersistentListP1-r10 N1PUCCH-AN-PersistentList
 }
 } OPTIONAL -- Need ON
 ]]
 }
}
SPS-ConfigUL ::= CHOICE {
 release NULL,
 setup SEQUENCE {
 semiPersistSchedIntervalUL ENUMERATED {
 sf10, sf20, sf32, sf40, sf64, sf80,
 sf128, sf160, sf320, sf640, spare6,
 spare5, spare4, spare3, spare2,
 spare1},
 implicitReleaseAfter ENUMERATED {e2, e3, e4, e8},
 p0-Persistent SEQUENCE { 
ETSI
3GPP TS 36.331 version 11.17.0 Release 11 298 ETSI TS 136 331 V11.17.0 (2017-02)
 p0-NominalPUSCH-Persistent INTEGER (-126..24),
 p0-UE-PUSCH-Persistent INTEGER (-8..7)
 } OPTIONAL, -- Need OP
 twoIntervalsConfig ENUMERATED {true} OPTIONAL, -- Cond TDD
 ...
 }
}
N1PUCCH-AN-PersistentList ::= SEQUENCE (SIZE (1..4)) OF INTEGER (0..2047)
TDD-Config ::= SEQUENCE {
 subframeAssignment ENUMERATED {
 sa0, sa1, sa2, sa3, sa4, sa5, sa6},
 specialSubframePatterns ENUMERATED {
 ssp0, ssp1, ssp2, ssp3, ssp4,ssp5, ssp6, ssp7,
 ssp8}
}
TDD-Config-v1130 ::= SEQUENCE {
 specialSubframePatterns-v1130 ENUMERATED {ssp7,ssp9}
}
TimeAlignmentTimer ::= ENUMERATED {
 sf500, sf750, sf1280, sf1920, sf2560, sf5120,
 sf10240, infinity} 
ETSI
3GPP TS 36.331 version 11.17.0 Release 11 300 ETSI TS 136 331 V11.17.0 (2017-02)
TPC-PDCCH-Config ::= CHOICE {
 release NULL,
 setup SEQUENCE {
 tpc-RNTI BIT STRING (SIZE (16)),
 tpc-Index TPC-Index
 }
}
TPC-Index ::= CHOICE {
 indexOfFormat3 INTEGER (1..15),
 indexOfFormat3A INTEGER (1..31)
}
ETSI
3GPP TS 36.331 version 11.17.0 Release 11 301 ETSI TS 136 331 V11.17.0 (2017-02)
UplinkPowerControlCommon ::= SEQUENCE {
 p0-NominalPUSCH INTEGER (-126..24),
 alpha ENUMERATED {al0, al04, al05, al06, al07, al08, al09, al1},
 p0-NominalPUCCH INTEGER (-127..-96),
 deltaFList-PUCCH DeltaFList-PUCCH,
 deltaPreambleMsg3 INTEGER (-1..6)
}
UplinkPowerControlCommon-v1020 ::= SEQUENCE {
 deltaF-PUCCH-Format3-r10 ENUMERATED {deltaF-1, deltaF0, deltaF1, deltaF2,
 deltaF3, deltaF4, deltaF5, deltaF6},
 deltaF-PUCCH-Format1bCS-r10 ENUMERATED {deltaF1, deltaF2, spare2, spare1}
}
UplinkPowerControlCommonSCell-r10 ::= SEQUENCE {
 p0-NominalPUSCH-r10 INTEGER (-126..24),
 alpha-r10 ENUMERATED {al0, al04, al05, al06, al07, al08, al09, al1}
}
UplinkPowerControlCommonSCell-v1130 ::= SEQUENCE {
 deltaPreambleMsg3-r11 INTEGER (-1..6)
}
UplinkPowerControlDedicated ::= SEQUENCE {
 p0-UE-PUSCH INTEGER (-8..7),
 deltaMCS-Enabled ENUMERATED {en0, en1},
 accumulationEnabled BOOLEAN,
 p0-UE-PUCCH INTEGER (-8..7),
 pSRS-Offset INTEGER (0..15),
 filterCoefficient FilterCoefficient DEFAULT fc4
}
UplinkPowerControlDedicated-v1020 ::= SEQUENCE {
 deltaTxD-OffsetListPUCCH-r10 DeltaTxD-OffsetListPUCCH-r10 OPTIONAL, -- Need OR 
ETSI
3GPP TS 36.331 version 11.17.0 Release 11 302 ETSI TS 136 331 V11.17.0 (2017-02)
 pSRS-OffsetAp-r10 INTEGER (0..15) OPTIONAL -- Need OR
}
UplinkPowerControlDedicated-v1130 ::= SEQUENCE {
 pSRS-Offset-v1130 INTEGER (16..31) OPTIONAL, -- Need OR
 pSRS-OffsetAp-v1130 INTEGER (16..31) OPTIONAL, -- Need OR
 deltaTxD-OffsetListPUCCH-v1130 DeltaTxD-OffsetListPUCCH-v1130 OPTIONAL -- Need OR
}
UplinkPowerControlDedicatedSCell-r10 ::= SEQUENCE {
 p0-UE-PUSCH-r10 INTEGER (-8..7),
 deltaMCS-Enabled-r10 ENUMERATED {en0, en1},
 accumulationEnabled-r10 BOOLEAN,
 pSRS-Offset-r10 INTEGER (0..15),
 pSRS-OffsetAp-r10 INTEGER (0..15) OPTIONAL, -- Need OR
 filterCoefficient-r10 FilterCoefficient DEFAULT fc4,
 pathlossReferenceLinking-r10 ENUMERATED {pCell, sCell}
}
DeltaFList-PUCCH ::= SEQUENCE {
 deltaF-PUCCH-Format1 ENUMERATED {deltaF-2, deltaF0, deltaF2},
 deltaF-PUCCH-Format1b ENUMERATED {deltaF1, deltaF3, deltaF5},
 deltaF-PUCCH-Format2 ENUMERATED {deltaF-2, deltaF0, deltaF1, deltaF2},
 deltaF-PUCCH-Format2a ENUMERATED {deltaF-2, deltaF0, deltaF2},
 deltaF-PUCCH-Format2b ENUMERATED {deltaF-2, deltaF0, deltaF2}
}
DeltaTxD-OffsetListPUCCH-r10 ::= SEQUENCE {
 deltaTxD-OffsetPUCCH-Format1-r10 ENUMERATED {dB0, dB-2},
 deltaTxD-OffsetPUCCH-Format1a1b-r10 ENUMERATED {dB0, dB-2},
 deltaTxD-OffsetPUCCH-Format22a2b-r10 ENUMERATED {dB0, dB-2},
 deltaTxD-OffsetPUCCH-Format3-r10 ENUMERATED {dB0, dB-2},
 ...
} 
ETSI
3GPP TS 36.331 version 11.17.0 Release 11 303 ETSI TS 136 331 V11.17.0 (2017-02)
DeltaTxD-OffsetListPUCCH-v1130 ::= SEQUENCE {
 deltaTxD-OffsetPUCCH-Format1bCS-r11 ENUMERATED {dB0, dB-1}
}
NextHopChainingCount ::= INTEGER (0..7)
SecurityAlgorithmConfig ::= SEQUENCE {
 cipheringAlgorithm ENUMERATED {
 eea0, eea1, eea2, eea3-v1130, spare4, spare3,
 spare2, spare1, ...},
 integrityProtAlgorithm ENUMERATED {
 eia0-v920, eia1, eia2, eia3-v1130, spare4, spare3,
 spare2, spare1, ...}
}
ShortMAC-I ::= BIT STRING (SIZE (16))
AdditionalSpectrumEmission ::= INTEGER (1..32)
ARFCN-ValueCDMA2000 ::= INTEGER (0..2047)
ARFCN-ValueEUTRA ::= INTEGER (0..maxEARFCN)
ARFCN-ValueEUTRA-v9e0 ::= INTEGER (maxEARFCN-Plus1..maxEARFCN2)
ARFCN-ValueEUTRA-r9 ::= INTEGER (0..maxEARFCN2)
ARFCN-ValueGERAN ::= INTEGER (0..1023)
ARFCN-ValueUTRA ::= INTEGER (0..16383)
BandclassCDMA2000 ::= ENUMERATED {
 bc0, bc1, bc2, bc3, bc4, bc5, bc6, bc7, bc8,
 bc9, bc10, bc11, bc12, bc13, bc14, bc15, bc16,
 bc17, bc18-v9a0, bc19-v9a0, bc20-v9a0, bc21-v9a0,
 spare10, spare9, spare8, spare7, spare6, spare5, spare4,
 spare3, spare2, spare1, ...}
BandIndicatorGERAN ::= ENUMERATED {dcs1800, pcs1900}
CarrierFreqCDMA2000 ::= SEQUENCE {
 bandClass BandclassCDMA2000,
 arfcn ARFCN-ValueCDMA2000 
ETSI
3GPP TS 36.331 version 11.17.0 Release 11 308 ETSI TS 136 331 V11.17.0 (2017-02)
}
CarrierFreqGERAN ::= SEQUENCE {
 arfcn ARFCN-ValueGERAN,
 bandIndicator BandIndicatorGERAN
}
CarrierFreqsGERAN ::= SEQUENCE {
 startingARFCN ARFCN-ValueGERAN,
 bandIndicator BandIndicatorGERAN,
 followingARFCNs CHOICE {
 explicitListOfARFCNs ExplicitListOfARFCNs,
 equallySpacedARFCNs SEQUENCE {
 arfcn-Spacing INTEGER (1..8),
 numberOfFollowingARFCNs INTEGER (0..31)
 }, 
ETSI
3GPP TS 36.331 version 11.17.0 Release 11 309 ETSI TS 136 331 V11.17.0 (2017-02)
 variableBitMapOfARFCNs OCTET STRING (SIZE (1..16))
 }
}
ExplicitListOfARFCNs ::= SEQUENCE (SIZE (0..31)) OF ARFCN-ValueGERAN
CarrierFreqListMBMS-r11 ::= SEQUENCE (SIZE (1..maxFreqMBMS-r11)) OF ARFCN-ValueEUTRA-r9
ETSI
3GPP TS 36.331 version 11.17.0 Release 11 310 ETSI TS 136 331 V11.17.0 (2017-02)
CDMA2000-Type ::= ENUMERATED {type1XRTT, typeHRPD}
CellIdentity ::= BIT STRING (SIZE (28))
CellIndexList ::= SEQUENCE (SIZE (1..maxCellMeas)) OF CellIndex
CellIndex ::= INTEGER (1..maxCellMeas)
CellReselectionPriority ::= INTEGER (0..7) 
ETSI
3GPP TS 36.331 version 11.17.0 Release 11 311 ETSI TS 136 331 V11.17.0 (2017-02)
CSFB-RegistrationParam1XRTT ::= SEQUENCE {
 sid BIT STRING (SIZE (15)),
 nid BIT STRING (SIZE (16)),
 multipleSID BOOLEAN,
 multipleNID BOOLEAN,
 homeReg BOOLEAN,
 foreignSIDReg BOOLEAN,
 foreignNIDReg BOOLEAN,
 parameterReg BOOLEAN,
 powerUpReg BOOLEAN,
 registrationPeriod BIT STRING (SIZE (7)),
 registrationZone BIT STRING (SIZE (12)),
 totalZone BIT STRING (SIZE (3)),
zoneTimer BIT STRING (SIZE (3))
}
CSFB-RegistrationParam1XRTT-v920 ::= SEQUENCE {
 powerDownReg-r9 ENUMERATED {true}
}
CellGlobalIdEUTRA ::= SEQUENCE {
 plmn-Identity PLMN-Identity,
 cellIdentity CellIdentity
}
CellGlobalIdUTRA ::= SEQUENCE {
 plmn-Identity PLMN-Identity,
 cellIdentity BIT STRING (SIZE (28))
}
CellGlobalIdGERAN ::= SEQUENCE {
 plmn-Identity PLMN-Identity,
 locationAreaCode BIT STRING (SIZE (16)),
 cellIdentity BIT STRING (SIZE (16))
}
CellGlobalIdCDMA2000 ::= CHOICE {
 cellGlobalId1XRTT BIT STRING (SIZE (47)),
 cellGlobalIdHRPD BIT STRING (SIZE (128))
}
CSG-Identity ::= BIT STRING (SIZE (27))
FreqBandIndicator ::= INTEGER (1..maxFBI) 
ETSI
3GPP TS 36.331 version 11.17.0 Release 11 315 ETSI TS 136 331 V11.17.0 (2017-02)
FreqBandIndicator-v9e0 ::= INTEGER (maxFBI-Plus1..maxFBI2)
FreqBandIndicator-r11 ::= INTEGER (1..maxFBI2)
MobilityControlInfo ::= SEQUENCE {
 targetPhysCellId PhysCellId,
 carrierFreq CarrierFreqEUTRA OPTIONAL, -- Cond HO-toEUTRA2
 carrierBandwidth CarrierBandwidthEUTRA OPTIONAL, -- Cond HO-toEUTRA
 additionalSpectrumEmission AdditionalSpectrumEmission OPTIONAL, -- Cond HO-toEUTRA
 t304 ENUMERATED {
 ms50, ms100, ms150, ms200, ms500, ms1000,
 ms2000, spare1},
 newUE-Identity C-RNTI,
 radioResourceConfigCommon RadioResourceConfigCommon,
 rach-ConfigDedicated RACH-ConfigDedicated OPTIONAL, -- Need OP
 ...,
 [[ carrierFreq-v9e0 CarrierFreqEUTRA-v9e0 OPTIONAL -- Need ON
 ]],
 [[ drb-ContinueROHC-r11 ENUMERATED {true} OPTIONAL -- Cond HO
 ]]
}
CarrierBandwidthEUTRA ::= SEQUENCE { 
ETSI
3GPP TS 36.331 version 11.17.0 Release 11 316 ETSI TS 136 331 V11.17.0 (2017-02)
 dl-Bandwidth ENUMERATED {
 n6, n15, n25, n50, n75, n100, spare10,
 spare9, spare8, spare7, spare6, spare5,
 spare4, spare3, spare2, spare1},
 ul-Bandwidth ENUMERATED {
 n6, n15, n25, n50, n75, n100, spare10,
 spare9, spare8, spare7, spare6, spare5,
 spare4, spare3, spare2, spare1} OPTIONAL -- Need OP
}
CarrierFreqEUTRA ::= SEQUENCE {
 dl-CarrierFreq ARFCN-ValueEUTRA,
 ul-CarrierFreq ARFCN-ValueEUTRA OPTIONAL -- Cond FDD
}
CarrierFreqEUTRA-v9e0 ::= SEQUENCE {
 dl-CarrierFreq-v9e0 ARFCN-ValueEUTRA-r9,
 ul-CarrierFreq-v9e0 ARFCN-ValueEUTRA-r9 OPTIONAL -- Cond FDD
}
MobilityParametersCDMA2000 ::= OCTET STRING
MobilityStateParameters ::= SEQUENCE {
 t-Evaluation ENUMERATED {
 s30, s60, s120, s180, s240, spare3, spare2, spare1},
 t-HystNormal ENUMERATED {
 s30, s60, s120, s180, s240, spare3, spare2, spare1},
 n-CellChangeMedium INTEGER (1..16),
 n-CellChangeHigh INTEGER (1..16)
}
MultiBandInfoList ::= SEQUENCE (SIZE (1..maxMultiBands)) OF FreqBandIndicator
MultiBandInfoList-v9e0 ::= SEQUENCE (SIZE (1..maxMultiBands)) OF MultiBandInfo-v9e0
MultiBandInfoList-v10j0 ::= SEQUENCE (SIZE (1..maxMultiBands)) OF NS-PmaxList-r10
MultiBandInfoList-r11 ::= SEQUENCE (SIZE (1..maxMultiBands)) OF FreqBandIndicator-r11
MultiBandInfo-v9e0 ::= SEQUENCE {
 freqBandIndicator-v9e0 FreqBandIndicator-v9e0 OPTIONAL -- Need OP 
ETSI
3GPP TS 36.331 version 11.17.0 Release 11 319 ETSI TS 136 331 V11.17.0 (2017-02)
}
NS-PmaxList-r10 ::= SEQUENCE (SIZE (1..maxNS-Pmax-r10)) OF NS-PmaxValue-r10
NS-PmaxValue-r10 ::= SEQUENCE {
 additionalPmax-r10 P-Max OPTIONAL, -- Need OP
 additionalSpectrumEmission AdditionalSpectrumEmission
}
PhysCellId ::= INTEGER (0..503)
PhysCellIdRange ::= SEQUENCE {
 start PhysCellId,
 range ENUMERATED {
 n4, n8, n12, n16, n24, n32, n48, n64, n84,
 n96, n128, n168, n252, n504, spare2,
 spare1} OPTIONAL -- Need OP
}
PhysCellIdRangeUTRA-FDDList-r9::= SEQUENCE (SIZE (1..maxPhysCellIdRange-r9)) OF
PhysCellIdRangeUTRA-FDD-r9
PhysCellIdRangeUTRA-FDD-r9 ::= SEQUENCE {
 start-r9 PhysCellIdUTRA-FDD,
 range-r9 INTEGER (2..512) OPTIONAL -- Need OP 
ETSI
3GPP TS 36.331 version 11.17.0 Release 11 321 ETSI TS 136 331 V11.17.0 (2017-02)
}
PhysCellIdCDMA2000 ::= INTEGER (0..maxPNOffset)
PhysCellIdGERAN ::= SEQUENCE {
 networkColourCode BIT STRING (SIZE (3)),
 baseStationColourCode BIT STRING (SIZE (3))
}
PhysCellIdUTRA-FDD ::= INTEGER (0..511)
PhysCellIdUTRA-TDD ::= INTEGER (0..127)
PLMN-Identity ::= SEQUENCE {
 mcc MCC OPTIONAL, -- Cond MCC
 mnc MNC
}
MCC ::= SEQUENCE (SIZE (3)) OF
 MCC-MNC-Digit
MNC ::= SEQUENCE (SIZE (2..3)) OF 
ETSI
3GPP TS 36.331 version 11.17.0 Release 11 323 ETSI TS 136 331 V11.17.0 (2017-02)
 MCC-MNC-Digit
MCC-MNC-Digit ::= INTEGER (0..9)
PLMN-IdentityList3-r11 ::= SEQUENCE (SIZE (1..16)) OF PLMN-Identity
PreRegistrationInfoHRPD ::= SEQUENCE {
 preRegistrationAllowed BOOLEAN,
 preRegistrationZoneId PreRegistrationZoneIdHRPD OPTIONAL, -- cond PreRegAllowed
 secondaryPreRegistrationZoneIdList SecondaryPreRegistrationZoneIdListHRPD OPTIONAL -- Need OR
}
SecondaryPreRegistrationZoneIdListHRPD ::= SEQUENCE (SIZE (1..2)) OF PreRegistrationZoneIdHRPD 
ETSI
3GPP TS 36.331 version 11.17.0 Release 11 324 ETSI TS 136 331 V11.17.0 (2017-02)
PreRegistrationZoneIdHRPD ::= INTEGER (0..255)
Q-QualMin-r9 ::= INTEGER (-34..-3)
Q-RxLevMin ::= INTEGER (-70..-22)
Q-OffsetRange ::= ENUMERATED {
 dB-24, dB-22, dB-20, dB-18, dB-16, dB-14,
 dB-12, dB-10, dB-8, dB-6, dB-5, dB-4, dB-3,
 dB-2, dB-1, dB0, dB1, dB2, dB3, dB4, dB5,
 dB6, dB8, dB10, dB12, dB14, dB16, dB18,
 dB20, dB22, dB24}
Q-OffsetRangeInterRAT ::= INTEGER (-15..15)
ReselectionThreshold ::= INTEGER (0..31)
ReselectionThresholdQ-r9 ::= INTEGER (0..31)
SCellIndex-r10 ::= INTEGER (1..7)
ServCellIndex-r10 ::= INTEGER (0..7)
SpeedStateScaleFactors ::= SEQUENCE {
 sf-Medium ENUMERATED {oDot25, oDot5, oDot75, lDot0},
 sf-High ENUMERATED {oDot25, oDot5, oDot75, lDot0}
}
SystemInfoListGERAN ::= SEQUENCE (SIZE (1..maxGERAN-SI)) OF
 OCTET STRING (SIZE (1..23))
SystemTimeInfoCDMA2000 ::= SEQUENCE {
 cdma-EUTRA-Synchronisation BOOLEAN,
 cdma-SystemTime CHOICE {
 synchronousSystemTime BIT STRING (SIZE (39)),
 asynchronousSystemTime BIT STRING (SIZE (49))
 }
}
TrackingAreaCode ::= BIT STRING (SIZE (16)) 
ETSI
3GPP TS 36.331 version 11.17.0 Release 11 329 ETSI TS 136 331 V11.17.0 (2017-02)
T-Reselection ::= INTEGER (0..7)
AllowedMeasBandwidth ::= ENUMERATED {mbw6, mbw15, mbw25, mbw50, mbw75, mbw100}
Hysteresis ::= INTEGER (0..30)
LocationInfo-r10 ::= SEQUENCE {
 locationCoordinates-r10 CHOICE {
 ellipsoid-Point-r10 OCTET STRING,
 ellipsoidPointWithAltitude-r10 OCTET STRING,
 ...,
 ellipsoidPointWithUncertaintyCircle-r11 OCTET STRING,
 ellipsoidPointWithUncertaintyEllipse-r11 OCTET STRING,
 ellipsoidPointWithAltitudeAndUncertaintyEllipsoid-r11 OCTET STRING,
 ellipsoidArc-r11 OCTET STRING,
 polygon-r11 OCTET STRING
 },
 horizontalVelocity-r10 OCTET STRING OPTIONAL,
 gnss-TOD-msec-r10 OCTET STRING OPTIONAL,
 ...
}
MeasConfig ::= SEQUENCE {
 -- Measurement objects
 measObjectToRemoveList MeasObjectToRemoveList OPTIONAL, -- Need ON
 measObjectToAddModList MeasObjectToAddModList OPTIONAL, -- Need ON
 -- Reporting configurations
 reportConfigToRemoveList ReportConfigToRemoveList OPTIONAL, -- Need ON
 reportConfigToAddModList ReportConfigToAddModList OPTIONAL, -- Need ON
 -- Measurement identities
 measIdToRemoveList MeasIdToRemoveList OPTIONAL, -- Need ON
 measIdToAddModList MeasIdToAddModList OPTIONAL, -- Need ON
 -- Other parameters
 quantityConfig QuantityConfig OPTIONAL, -- Need ON
 measGapConfig MeasGapConfig OPTIONAL, -- Need ON
 s-Measure RSRP-Range OPTIONAL, -- Need ON 
ETSI
3GPP TS 36.331 version 11.17.0 Release 11 332 ETSI TS 136 331 V11.17.0 (2017-02)
 preRegistrationInfoHRPD PreRegistrationInfoHRPD OPTIONAL, -- Need OP
 speedStatePars CHOICE {
 release NULL,
 setup SEQUENCE {
 mobilityStateParameters MobilityStateParameters,
 timeToTrigger-SF SpeedStateScaleFactors
 }
 } OPTIONAL, -- Need ON
 ...,
 [[ measObjectToAddModList-v9e0 MeasObjectToAddModList-v9e0 OPTIONAL -- Need ON
 ]],
 [[ allowInterruptions-r11 BOOLEAN OPTIONAL -- Need ON
 ]]
}
MeasIdToRemoveList ::= SEQUENCE (SIZE (1..maxMeasId)) OF MeasId
MeasObjectToRemoveList ::= SEQUENCE (SIZE (1..maxObjectId)) OF MeasObjectId
ReportConfigToRemoveList ::= SEQUENCE (SIZE (1..maxReportConfigId)) OF ReportConfigId
MeasGapConfig ::= CHOICE {
release NULL,
 setup SEQUENCE {
 gapOffset CHOICE {
 gp0 INTEGER (0..39),
 gp1 INTEGER (0..79),
 ...
 }
 }
}
MeasId ::= INTEGER (1..maxMeasId) 
ETSI
3GPP TS 36.331 version 11.17.0 Release 11 334 ETSI TS 136 331 V11.17.0 (2017-02)
MeasIdToAddModList ::= SEQUENCE (SIZE (1..maxMeasId)) OF MeasIdToAddMod
MeasIdToAddMod ::= SEQUENCE {
 measId MeasId,
 measObjectId MeasObjectId,
 reportConfigId ReportConfigId
}
MeasObjectCDMA2000 ::= SEQUENCE {
 cdma2000-Type CDMA2000-Type,
 carrierFreq CarrierFreqCDMA2000,
 searchWindowSize INTEGER (0..15) OPTIONAL, -- Need ON
 offsetFreq Q-OffsetRangeInterRAT DEFAULT 0,
 cellsToRemoveList CellIndexList OPTIONAL, -- Need ON
 cellsToAddModList CellsToAddModListCDMA2000 OPTIONAL, -- Need ON
 cellForWhichToReportCGI PhysCellIdCDMA2000 OPTIONAL, -- Need ON
 ...
} 
ETSI
3GPP TS 36.331 version 11.17.0 Release 11 335 ETSI TS 136 331 V11.17.0 (2017-02)
CellsToAddModListCDMA2000 ::= SEQUENCE (SIZE (1..maxCellMeas)) OF CellsToAddModCDMA2000
CellsToAddModCDMA2000 ::= SEQUENCE {
 cellIndex INTEGER (1..maxCellMeas),
 physCellId PhysCellIdCDMA2000
}
MeasObjectEUTRA ::= SEQUENCE {
 carrierFreq ARFCN-ValueEUTRA,
 allowedMeasBandwidth AllowedMeasBandwidth,
 presenceAntennaPort1 PresenceAntennaPort1,
 neighCellConfig NeighCellConfig,
 offsetFreq Q-OffsetRange DEFAULT dB0,
 -- Cell list
 cellsToRemoveList CellIndexList OPTIONAL, -- Need ON
 cellsToAddModList CellsToAddModList OPTIONAL, -- Need ON
 -- Black list 
ETSI
3GPP TS 36.331 version 11.17.0 Release 11 336 ETSI TS 136 331 V11.17.0 (2017-02)
 blackCellsToRemoveList CellIndexList OPTIONAL, -- Need ON
 blackCellsToAddModList BlackCellsToAddModList OPTIONAL, -- Need ON
 cellForWhichToReportCGI PhysCellId OPTIONAL, -- Need ON
 ...,
 [[measCycleSCell-r10 MeasCycleSCell-r10 OPTIONAL, -- Need ON
 measSubframePatternConfigNeigh-r10 MeasSubframePatternConfigNeigh-r10 OPTIONAL
 -- Need ON
 ]],
 [[widebandRSRQ-Meas-r11 BOOLEAN OPTIONAL -- Cond WB-RSRQ
 ]]
}
MeasObjectEUTRA-v9e0 ::= SEQUENCE {
 carrierFreq-v9e0 ARFCN-ValueEUTRA-v9e0
}
CellsToAddModList ::= SEQUENCE (SIZE (1..maxCellMeas)) OF CellsToAddMod
CellsToAddMod ::= SEQUENCE {
 cellIndex INTEGER (1..maxCellMeas),
 physCellId PhysCellId,
 cellIndividualOffset Q-OffsetRange
}
BlackCellsToAddModList ::= SEQUENCE (SIZE (1..maxCellMeas)) OF BlackCellsToAddMod
BlackCellsToAddMod ::= SEQUENCE {
 cellIndex INTEGER (1..maxCellMeas),
 physCellIdRange PhysCellIdRange
}
MeasCycleSCell-r10 ::= ENUMERATED {sf160, sf256, sf320, sf512,
 sf640, sf1024, sf1280, spare1}
MeasSubframePatternConfigNeigh-r10 ::= CHOICE { 
ETSI
3GPP TS 36.331 version 11.17.0 Release 11 337 ETSI TS 136 331 V11.17.0 (2017-02)
 release NULL,
 setup SEQUENCE {
 measSubframePatternNeigh-r10 MeasSubframePattern-r10,
 measSubframeCellList-r10 MeasSubframeCellList-r10 OPTIONAL -- Cond always
 }
}
MeasSubframeCellList-r10 ::= SEQUENCE (SIZE (1..maxCellMeas)) OF PhysCellIdRange
MeasObjectGERAN ::= SEQUENCE {
 carrierFreqs CarrierFreqsGERAN,
 offsetFreq Q-OffsetRangeInterRAT DEFAULT 0,
 ncc-Permitted BIT STRING(SIZE (8)) DEFAULT '11111111'B,
 cellForWhichToReportCGI PhysCellIdGERAN OPTIONAL, -- Need ON
 ...
}
MeasObjectId ::= INTEGER (1..maxObjectId)
MeasObjectToAddModList ::= SEQUENCE (SIZE (1..maxObjectId)) OF MeasObjectToAddMod
MeasObjectToAddModList-v9e0 ::= SEQUENCE (SIZE (1..maxObjectId)) OF MeasObjectToAddMod-v9e0
MeasObjectToAddMod ::= SEQUENCE {
 measObjectId MeasObjectId,
 measObject CHOICE {
 measObjectEUTRA MeasObjectEUTRA,
 measObjectUTRA MeasObjectUTRA,
 measObjectGERAN MeasObjectGERAN,
 measObjectCDMA2000 MeasObjectCDMA2000,
 ...
 }
}
MeasObjectToAddMod-v9e0 ::= SEQUENCE {
 measObjectEUTRA-v9e0 MeasObjectEUTRA-v9e0 OPTIONAL -- Cond eutra
}
ETSI
3GPP TS 36.331 version 11.17.0 Release 11 340 ETSI TS 136 331 V11.17.0 (2017-02)
MeasObjectUTRA ::= SEQUENCE {
 carrierFreq ARFCN-ValueUTRA,
 offsetFreq Q-OffsetRangeInterRAT DEFAULT 0,
 cellsToRemoveList CellIndexList OPTIONAL, -- Need ON
 cellsToAddModList CHOICE {
 cellsToAddModListUTRA-FDD CellsToAddModListUTRA-FDD,
 cellsToAddModListUTRA-TDD CellsToAddModListUTRA-TDD
 } OPTIONAL, -- Need ON
 cellForWhichToReportCGI CHOICE {
 utra-FDD PhysCellIdUTRA-FDD,
 utra-TDD PhysCellIdUTRA-TDD
 } OPTIONAL, -- Need ON
 ...,
 [[ csg-allowedReportingCells-v930 CSG-AllowedReportingCells-r9 OPTIONAL -- Need ON
 ]]
}
CellsToAddModListUTRA-FDD ::= SEQUENCE (SIZE (1..maxCellMeas)) OF CellsToAddModUTRA-FDD
CellsToAddModUTRA-FDD ::= SEQUENCE {
 cellIndex INTEGER (1..maxCellMeas),
 physCellId PhysCellIdUTRA-FDD
}
CellsToAddModListUTRA-TDD ::= SEQUENCE (SIZE (1..maxCellMeas)) OF CellsToAddModUTRA-TDD
CellsToAddModUTRA-TDD ::= SEQUENCE {
 cellIndex INTEGER (1..maxCellMeas),
 physCellId PhysCellIdUTRA-TDD
}
CSG-AllowedReportingCells-r9 ::= SEQUENCE {
 physCellIdRangeUTRA-FDDList-r9 PhysCellIdRangeUTRA-FDDList-r9 OPTIONAL -- Need OR
} 
ETSI
3GPP TS 36.331 version 11.17.0 Release 11 341 ETSI TS 136 331 V11.17.0 (2017-02)
MeasResults ::= SEQUENCE {
 measId MeasId,
 measResultPCell SEQUENCE {
 rsrpResult RSRP-Range,
 rsrqResult RSRQ-Range
 },
 measResultNeighCells CHOICE {
 measResultListEUTRA MeasResultListEUTRA,
 measResultListUTRA MeasResultListUTRA,
 measResultListGERAN MeasResultListGERAN,
 measResultsCDMA2000 MeasResultsCDMA2000,
 ...
 } OPTIONAL,
 ...,
 [[ measResultForECID-r9 MeasResultForECID-r9 OPTIONAL
 ]],
 [[ locationInfo-r10 LocationInfo-r10 OPTIONAL,
 measResultServFreqList-r10 MeasResultServFreqList-r10 OPTIONAL
 ]] 
ETSI
3GPP TS 36.331 version 11.17.0 Release 11 342 ETSI TS 136 331 V11.17.0 (2017-02)
}
MeasResultListEUTRA ::= SEQUENCE (SIZE (1..maxCellReport)) OF MeasResultEUTRA
MeasResultEUTRA ::= SEQUENCE {
 physCellId PhysCellId,
 cgi-Info SEQUENCE {
 cellGlobalId CellGlobalIdEUTRA,
 trackingAreaCode TrackingAreaCode,
 plmn-IdentityList PLMN-IdentityList2 OPTIONAL
 } OPTIONAL,
 measResult SEQUENCE {
 rsrpResult RSRP-Range OPTIONAL,
 rsrqResult RSRQ-Range OPTIONAL,
 ...,
 [[ additionalSI-Info-r9 AdditionalSI-Info-r9 OPTIONAL
 ]]
 }
}
MeasResultServFreqList-r10 ::= SEQUENCE (SIZE (1..maxServCell-r10)) OF MeasResultServFreq-r10
MeasResultServFreq-r10 ::= SEQUENCE {
 servFreqId-r10 ServCellIndex-r10,
 measResultSCell-r10 SEQUENCE {
 rsrpResultSCell-r10 RSRP-Range,
 rsrqResultSCell-r10 RSRQ-Range
 } OPTIONAL,
 measResultBestNeighCell-r10 SEQUENCE {
 physCellId-r10 PhysCellId,
 rsrpResultNCell-r10 RSRP-Range,
 rsrqResultNCell-r10 RSRQ-Range
 } OPTIONAL,
 ...
} 
ETSI
3GPP TS 36.331 version 11.17.0 Release 11 343 ETSI TS 136 331 V11.17.0 (2017-02)
MeasResultListUTRA ::= SEQUENCE (SIZE (1..maxCellReport)) OF MeasResultUTRA
MeasResultUTRA ::= SEQUENCE {
 physCellId CHOICE {
 fdd PhysCellIdUTRA-FDD,
 tdd PhysCellIdUTRA-TDD
 },
 cgi-Info SEQUENCE {
 cellGlobalId CellGlobalIdUTRA,
 locationAreaCode BIT STRING (SIZE (16)) OPTIONAL,
 routingAreaCode BIT STRING (SIZE (8)) OPTIONAL,
 plmn-IdentityList PLMN-IdentityList2 OPTIONAL
 } OPTIONAL,
 measResult SEQUENCE {
 utra-RSCP INTEGER (-5..91) OPTIONAL,
 utra-EcN0 INTEGER (0..49) OPTIONAL,
 ...,
 [[ additionalSI-Info-r9 AdditionalSI-Info-r9 OPTIONAL
 ]]
 }
}
MeasResultListGERAN ::= SEQUENCE (SIZE (1..maxCellReport)) OF MeasResultGERAN
MeasResultGERAN ::= SEQUENCE {
 carrierFreq CarrierFreqGERAN,
 physCellId PhysCellIdGERAN,
 cgi-Info SEQUENCE {
 cellGlobalId CellGlobalIdGERAN,
 routingAreaCode BIT STRING (SIZE (8)) OPTIONAL
 } OPTIONAL,
 measResult SEQUENCE {
 rssi INTEGER (0..63),
 ... 
ETSI
3GPP TS 36.331 version 11.17.0 Release 11 344 ETSI TS 136 331 V11.17.0 (2017-02)
 }
}
MeasResultsCDMA2000 ::= SEQUENCE {
 preRegistrationStatusHRPD BOOLEAN,
 measResultListCDMA2000 MeasResultListCDMA2000
}
MeasResultListCDMA2000 ::= SEQUENCE (SIZE (1..maxCellReport)) OF MeasResultCDMA2000
MeasResultCDMA2000 ::= SEQUENCE {
 physCellId PhysCellIdCDMA2000,
 cgi-Info CellGlobalIdCDMA2000 OPTIONAL,
 measResult SEQUENCE {
 pilotPnPhase INTEGER (0..32767) OPTIONAL,
 pilotStrength INTEGER (0..63),
 ...
 }
}
MeasResultForECID-r9 ::= SEQUENCE {
 ue-RxTxTimeDiffResult-r9 INTEGER (0..4095),
 currentSFN-r9 BIT STRING (SIZE (10))
}
PLMN-IdentityList2 ::= SEQUENCE (SIZE (1..5)) OF PLMN-Identity
AdditionalSI-Info-r9 ::= SEQUENCE {
 csg-MemberStatus-r9 ENUMERATED {member} OPTIONAL,
 csg-Identity-r9 CSG-Identity OPTIONAL
}
QuantityConfig ::= SEQUENCE {
 quantityConfigEUTRA QuantityConfigEUTRA OPTIONAL, -- Need ON
 quantityConfigUTRA QuantityConfigUTRA OPTIONAL, -- Need ON
 quantityConfigGERAN QuantityConfigGERAN OPTIONAL, -- Need ON
 quantityConfigCDMA2000 QuantityConfigCDMA2000 OPTIONAL, -- Need ON
 ...,
 [[ quantityConfigUTRA-v1020 QuantityConfigUTRA-v1020 OPTIONAL -- Need ON
 ]]
}
QuantityConfigEUTRA ::= SEQUENCE {
 filterCoefficientRSRP FilterCoefficient DEFAULT fc4,
 filterCoefficientRSRQ FilterCoefficient DEFAULT fc4
}
QuantityConfigUTRA ::= SEQUENCE {
 measQuantityUTRA-FDD ENUMERATED {cpich-RSCP, cpich-EcN0},
 measQuantityUTRA-TDD ENUMERATED {pccpch-RSCP},
 filterCoefficient FilterCoefficient DEFAULT fc4
}
QuantityConfigUTRA-v1020 ::= SEQUENCE {
 filterCoefficient2-FDD-r10 FilterCoefficient DEFAULT fc4
}
QuantityConfigGERAN ::= SEQUENCE {
 measQuantityGERAN ENUMERATED {rssi},
 filterCoefficient FilterCoefficient DEFAULT fc2
} 
ETSI
3GPP TS 36.331 version 11.17.0 Release 11 347 ETSI TS 136 331 V11.17.0 (2017-02)
QuantityConfigCDMA2000 ::= SEQUENCE {
 measQuantityCDMA2000 ENUMERATED {pilotStrength, pilotPnPhaseAndPilotStrength}
}
ReportConfigEUTRA ::= SEQUENCE {
 triggerType CHOICE { 
ETSI
3GPP TS 36.331 version 11.17.0 Release 11 348 ETSI TS 136 331 V11.17.0 (2017-02)
 event SEQUENCE {
 eventId CHOICE {
 eventA1 SEQUENCE {
 a1-Threshold ThresholdEUTRA
 },
 eventA2 SEQUENCE {
 a2-Threshold ThresholdEUTRA
 },
 eventA3 SEQUENCE {
 a3-Offset INTEGER (-30..30),
 reportOnLeave BOOLEAN
 },
 eventA4 SEQUENCE {
 a4-Threshold ThresholdEUTRA
 },
 eventA5 SEQUENCE {
 a5-Threshold1 ThresholdEUTRA,
 a5-Threshold2 ThresholdEUTRA
 },
 ...,
 eventA6-r10 SEQUENCE {
 a6-Offset-r10 INTEGER (-30..30),
 a6-ReportOnLeave-r10 BOOLEAN
 }
 },
 hysteresis Hysteresis,
 timeToTrigger TimeToTrigger
 },
 periodical SEQUENCE {
 purpose ENUMERATED {
 reportStrongestCells, reportCGI}
 }
 },
 triggerQuantity ENUMERATED {rsrp, rsrq},
 reportQuantity ENUMERATED {sameAsTriggerQuantity, both}, 
ETSI
3GPP TS 36.331 version 11.17.0 Release 11 349 ETSI TS 136 331 V11.17.0 (2017-02)
 maxReportCells INTEGER (1..maxCellReport),
 reportInterval ReportInterval,
 reportAmount ENUMERATED {r1, r2, r4, r8, r16, r32, r64, infinity},
 ...,
 [[ si-RequestForHO-r9 ENUMERATED {setup} OPTIONAL, -- Cond reportCGI
 ue-RxTxTimeDiffPeriodical-r9 ENUMERATED {setup} OPTIONAL -- Need OR
 ]],
 [[ includeLocationInfo-r10 ENUMERATED {true} OPTIONAL, -- Need OR
 reportAddNeighMeas-r10 ENUMERATED {setup} OPTIONAL -- Need OR
 ]]
}
ThresholdEUTRA ::= CHOICE{
 threshold-RSRP RSRP-Range,
 threshold-RSRQ RSRQ-Range
}
ReportConfigId ::= INTEGER (1..maxReportConfigId)
ReportConfigInterRAT ::= SEQUENCE {
 triggerType CHOICE {
 event SEQUENCE {
 eventId CHOICE {
 eventB1 SEQUENCE {
 b1-Threshold CHOICE {
 b1-ThresholdUTRA ThresholdUTRA,
 b1-ThresholdGERAN ThresholdGERAN,
 b1-ThresholdCDMA2000 ThresholdCDMA2000
 }
 },
 eventB2 SEQUENCE {
 b2-Threshold1 ThresholdEUTRA,
 b2-Threshold2 CHOICE {
 b2-Threshold2UTRA ThresholdUTRA,
 b2-Threshold2GERAN ThresholdGERAN,
 b2-Threshold2CDMA2000 ThresholdCDMA2000
 }
 },
 ...
 },
 hysteresis Hysteresis,
 timeToTrigger TimeToTrigger
 },
 periodical SEQUENCE { 
ETSI
3GPP TS 36.331 version 11.17.0 Release 11 352 ETSI TS 136 331 V11.17.0 (2017-02)
 purpose ENUMERATED {
 reportStrongestCells,
 reportStrongestCellsForSON,
 reportCGI}
 }
 },
 maxReportCells INTEGER (1..maxCellReport),
 reportInterval ReportInterval,
 reportAmount ENUMERATED {r1, r2, r4, r8, r16, r32, r64, infinity},
 ...,
 [[ si-RequestForHO-r9 ENUMERATED {setup} OPTIONAL -- Cond reportCGI
 ]],
 [[ reportQuantityUTRA-FDD-r10 ENUMERATED {both} OPTIONAL -- Need OR
 ]],
 [[ includeLocationInfo-r11 BOOLEAN OPTIONAL -- Need ON
 ]]
}
ThresholdUTRA ::= CHOICE{
 utra-RSCP INTEGER (-5..91),
 utra-EcN0 INTEGER (0..49)
}
ThresholdGERAN ::= INTEGER (0..63)
ThresholdCDMA2000 ::= INTEGER (0..63)
ReportConfigToAddModList ::= SEQUENCE (SIZE (1..maxReportConfigId)) OF ReportConfigToAddMod
ReportConfigToAddMod ::= SEQUENCE {
 reportConfigId ReportConfigId,
 reportConfig CHOICE {
 reportConfigEUTRA ReportConfigEUTRA,
 reportConfigInterRAT ReportConfigInterRAT
 }
} 
ETSI
3GPP TS 36.331 version 11.17.0 Release 11 354 ETSI TS 136 331 V11.17.0 (2017-02)
ReportInterval ::= ENUMERATED {
 ms120, ms240, ms480, ms640, ms1024, ms2048, ms5120, ms10240,
 min1, min6, min12, min30, min60, spare3, spare2, spare1}
RSRP-Range ::= INTEGER(0..97)
RSRQ-Range ::= INTEGER(0..34) 
ETSI
3GPP TS 36.331 version 11.17.0 Release 11 355 ETSI TS 136 331 V11.17.0 (2017-02)
TimeToTrigger ::= ENUMERATED {
 ms0, ms40, ms64, ms80, ms100, ms128, ms160, ms256,
 ms320, ms480, ms512, ms640, ms1024, ms1280, ms2560,
 ms5120}
AbsoluteTimeInfo-r10 ::= BIT STRING (SIZE (48))
AreaConfiguration-r10 ::= CHOICE { 
ETSI
3GPP TS 36.331 version 11.17.0 Release 11 356 ETSI TS 136 331 V11.17.0 (2017-02)
 cellGlobalIdList-r10 CellGlobalIdList-r10,
 trackingAreaCodeList-r10 TrackingAreaCodeList-r10
}
AreaConfiguration-v1130 ::= SEQUENCE {
 trackingAreaCodeList-v1130 TrackingAreaCodeList-v1130
}
CellGlobalIdList-r10 ::= SEQUENCE (SIZE (1..32)) OF CellGlobalIdEUTRA
TrackingAreaCodeList-r10 ::= SEQUENCE (SIZE (1..8)) OF TrackingAreaCode
TrackingAreaCodeList-v1130 ::= SEQUENCE {
 plmn-Identity-perTAC-List-r11 SEQUENCE (SIZE (1..8)) OF PLMN-Identity
}
C-RNTI ::= BIT STRING (SIZE (16))
DedicatedInfoCDMA2000 ::= OCTET STRING
DedicatedInfoNAS ::= OCTET STRING
FilterCoefficient ::= ENUMERATED {
 fc0, fc1, fc2, fc3, fc4, fc5,
 fc6, fc7, fc8, fc9, fc11, fc13,
 fc15, fc17, fc19, spare1, ...}
LoggingDuration-r10 ::= ENUMERATED {
 min10, min20, min40, min60, min90, min120, spare2, spare1}
LoggingInterval-r10 ::= ENUMERATED {
 ms1280, ms2560, ms5120, ms10240, ms20480,
 ms30720, ms40960, ms61440}
MeasSubframePattern-r10 ::= CHOICE {
 subframePatternFDD-r10 BIT STRING (SIZE (40)),
 subframePatternTDD-r10 CHOICE {
 subframeConfig1-5-r10 BIT STRING (SIZE (20)),
 subframeConfig0-r10 BIT STRING (SIZE (70)), 
ETSI
3GPP TS 36.331 version 11.17.0 Release 11 359 ETSI TS 136 331 V11.17.0 (2017-02)
 subframeConfig6-r10 BIT STRING (SIZE (60)),
 ...
 },
 ...
}
MMEC ::= BIT STRING (SIZE (8))
NeighCellConfig ::= BIT STRING (SIZE (2))
OtherConfig-r9 ::= SEQUENCE {
 reportProximityConfig-r9 ReportProximityConfig-r9 OPTIONAL, -- Need ON
 ...,
 [[ idc-Config-r11 IDC-Config-r11 OPTIONAL, -- Need ON
 powerPrefIndicationConfig-r11 PowerPrefIndicationConfig-r11 OPTIONAL, -- Need ON
 obtainLocationConfig-r11 ObtainLocationConfig-r11 OPTIONAL -- Need ON
 ]]
}
IDC-Config-r11 ::= SEQUENCE {
 idc-Indication-r11 ENUMERATED {setup} OPTIONAL, -- Need OR
 autonomousDenialParameters-r11 SEQUENCE {
 autonomousDenialSubframes-r11 ENUMERATED {n2, n5, n10, n15,
 n20, n30, spare2, spare1},
 autonomousDenialValidity-r11 ENUMERATED {
 sf200, sf500, sf1000, sf2000,
 spare4, spare3, spare2, spare1}
 } OPTIONAL, -- Need OR
 ...,
 [[ idc-Indication-UL-CA-r11 ENUMERATED {setup} OPTIONAL -- Cond idc-Ind
 ]]
} 
ETSI
3GPP TS 36.331 version 11.17.0 Release 11 361 ETSI TS 136 331 V11.17.0 (2017-02)
ObtainLocationConfig-r11 ::= SEQUENCE {
 obtainLocation-r11 ENUMERATED {setup} OPTIONAL -- Need OR
}
PowerPrefIndicationConfig-r11 ::= CHOICE{
 release NULL,
 setup SEQUENCE{
 powerPrefIndicationTimer-r11 ENUMERATED {s0, s0dot5, s1, s2, s5, s10, s20,
 s30, s60, s90, s120, s300, s600, spare3,
 spare2, spare1}
 }
}
ReportProximityConfig-r9 ::= SEQUENCE {
 proximityIndicationEUTRA-r9 ENUMERATED {enabled} OPTIONAL, -- Need OR
 proximityIndicationUTRA-r9 ENUMERATED {enabled} OPTIONAL -- Need OR
}
RAND-CDMA2000 ::= BIT STRING (SIZE (32))
RAT-Type ::= ENUMERATED {
 eutra, utra, geran-cs, geran-ps, cdma2000-1XRTT,
 spare3, spare2, spare1, ...}
RRC-TransactionIdentifier ::= INTEGER (0..3)
S-TMSI ::= SEQUENCE {
 mmec MMEC,
 m-TMSI BIT STRING (SIZE (32))
}
TraceReference-r10 ::= SEQUENCE {
 plmn-Identity-r10 PLMN-Identity,
 traceId-r10 OCTET STRING (SIZE (3))
}
ETSI
3GPP TS 36.331 version 11.17.0 Release 11 364 ETSI TS 136 331 V11.17.0 (2017-02)
UE-CapabilityRAT-ContainerList ::=SEQUENCE (SIZE (0..maxRAT-Capabilities)) OF UE-CapabilityRAT-Container
UE-CapabilityRAT-Container ::= SEQUENCE {
 rat-Type RAT-Type,
 ueCapabilityRAT-Container OCTET STRING
}
UE-EUTRA-Capability ::= SEQUENCE {
 accessStratumRelease AccessStratumRelease,
 ue-Category INTEGER (1..5),
 pdcp-Parameters PDCP-Parameters, 
ETSI
3GPP TS 36.331 version 11.17.0 Release 11 365 ETSI TS 136 331 V11.17.0 (2017-02)
 phyLayerParameters PhyLayerParameters,
 rf-Parameters RF-Parameters,
 measParameters MeasParameters,
 featureGroupIndicators BIT STRING (SIZE (32)) OPTIONAL,
 interRAT-Parameters SEQUENCE {
 utraFDD IRAT-ParametersUTRA-FDD OPTIONAL,
 utraTDD128 IRAT-ParametersUTRA-TDD128 OPTIONAL,
 utraTDD384 IRAT-ParametersUTRA-TDD384 OPTIONAL,
 utraTDD768 IRAT-ParametersUTRA-TDD768 OPTIONAL,
 geran IRAT-ParametersGERAN OPTIONAL,
 cdma2000-HRPD IRAT-ParametersCDMA2000-HRPD OPTIONAL,
 cdma2000-1xRTT IRAT-ParametersCDMA2000-1XRTT OPTIONAL
 },
 nonCriticalExtension UE-EUTRA-Capability-v920-IEs OPTIONAL
}
-- Late non critical extensions
UE-EUTRA-Capability-v9a0-IEs ::= SEQUENCE {
 featureGroupIndRel9Add-r9 BIT STRING (SIZE (32)) OPTIONAL,
 fdd-Add-UE-EUTRA-Capabilities-r9 UE-EUTRA-CapabilityAddXDD-Mode-r9 OPTIONAL,
 tdd-Add-UE-EUTRA-Capabilities-r9 UE-EUTRA-CapabilityAddXDD-Mode-r9 OPTIONAL,
 nonCriticalExtension UE-EUTRA-Capability-v9c0-IEs OPTIONAL
}
UE-EUTRA-Capability-v9c0-IEs ::= SEQUENCE {
 interRAT-ParametersUTRA-v9c0 IRAT-ParametersUTRA-v9c0 OPTIONAL,
 nonCriticalExtension UE-EUTRA-Capability-v9d0-IEs OPTIONAL
}
UE-EUTRA-Capability-v9d0-IEs ::= SEQUENCE {
 phyLayerParameters-v9d0 PhyLayerParameters-v9d0 OPTIONAL,
 nonCriticalExtension UE-EUTRA-Capability-v9e0-IEs OPTIONAL
}
UE-EUTRA-Capability-v9e0-IEs ::= SEQUENCE { 
ETSI
3GPP TS 36.331 version 11.17.0 Release 11 366 ETSI TS 136 331 V11.17.0 (2017-02)
 rf-Parameters-v9e0 RF-Parameters-v9e0 OPTIONAL,
 nonCriticalExtension UE-EUTRA-Capability-v9h0-IEs OPTIONAL
}
UE-EUTRA-Capability-v9h0-IEs ::= SEQUENCE {
 interRAT-ParametersUTRA-v9h0 IRAT-ParametersUTRA-v9h0 OPTIONAL,
 -- Following field is only to be used for late REL-9 extensions
 lateNonCriticalExtension OCTET STRING OPTIONAL,
 nonCriticalExtension UE-EUTRA-Capability-v10c0-IEs OPTIONAL
}
UE-EUTRA-Capability-v10c0-IEs ::= SEQUENCE {
 otdoa-PositioningCapabilities-r10 OTDOA-PositioningCapabilities-r10 OPTIONAL,
 nonCriticalExtension UE-EUTRA-Capability-v10f0-IEs OPTIONAL
}
UE-EUTRA-Capability-v10f0-IEs ::= SEQUENCE {
 rf-Parameters-v10f0 RF-Parameters-v10f0 OPTIONAL,
 nonCriticalExtension UE-EUTRA-Capability-v10i0-IEs OPTIONAL
}
UE-EUTRA-Capability-v10i0-IEs ::= SEQUENCE {
 rf-Parameters-v10i0 RF-Parameters-v10i0 OPTIONAL,
 -- Following field is only to be used for late REL-10 extensions
 lateNonCriticalExtension OCTET STRING (CONTAINING UE-EUTRA-Capability-v10j0-IEs)
 OPTIONAL,
 nonCriticalExtension UE-EUTRA-Capability-v11d0-IEs OPTIONAL
}
UE-EUTRA-Capability-v10j0-IEs ::= SEQUENCE {
 rf-Parameters-v10j0 RF-Parameters-v10j0 OPTIONAL,
 nonCriticalExtension SEQUENCE {} OPTIONAL
}
UE-EUTRA-Capability-v11d0-IEs ::= SEQUENCE { 
ETSI
3GPP TS 36.331 version 11.17.0 Release 11 367 ETSI TS 136 331 V11.17.0 (2017-02)
 rf-Parameters-v11d0 RF-Parameters-v11d0 OPTIONAL,
 otherParameters-v11d0 Other-Parameters-v11d0 OPTIONAL,
 -- Following field is only to be used for late REL-11 extensions
 nonCriticalExtension SEQUENCE {} OPTIONAL
}
-- Regular non critical extensions
UE-EUTRA-Capability-v920-IEs ::= SEQUENCE {
 phyLayerParameters-v920 PhyLayerParameters-v920,
 interRAT-ParametersGERAN-v920 IRAT-ParametersGERAN-v920,
 interRAT-ParametersUTRA-v920 IRAT-ParametersUTRA-v920 OPTIONAL,
 interRAT-ParametersCDMA2000-v920 IRAT-ParametersCDMA2000-1XRTT-v920 OPTIONAL,
 deviceType-r9 ENUMERATED {noBenFromBatConsumpOpt} OPTIONAL,
 csg-ProximityIndicationParameters-r9 CSG-ProximityIndicationParameters-r9,
 neighCellSI-AcquisitionParameters-r9 NeighCellSI-AcquisitionParameters-r9,
 son-Parameters-r9 SON-Parameters-r9,
 nonCriticalExtension UE-EUTRA-Capability-v940-IEs OPTIONAL
}
UE-EUTRA-Capability-v940-IEs ::= SEQUENCE {
 lateNonCriticalExtension OCTET STRING (CONTAINING UE-EUTRA-Capability-v9a0-IEs)
 OPTIONAL,
 nonCriticalExtension UE-EUTRA-Capability-v1020-IEs OPTIONAL
}
UE-EUTRA-Capability-v1020-IEs ::= SEQUENCE {
 ue-Category-v1020 INTEGER (6..8) OPTIONAL,
 phyLayerParameters-v1020 PhyLayerParameters-v1020 OPTIONAL,
 rf-Parameters-v1020 RF-Parameters-v1020 OPTIONAL,
 measParameters-v1020 MeasParameters-v1020 OPTIONAL,
 featureGroupIndRel10-r10 BIT STRING (SIZE (32)) OPTIONAL,
 interRAT-ParametersCDMA2000-v1020 IRAT-ParametersCDMA2000-1XRTT-v1020 OPTIONAL,
 ue-BasedNetwPerfMeasParameters-r10 UE-BasedNetwPerfMeasParameters-r10 OPTIONAL,
 interRAT-ParametersUTRA-TDD-v1020 IRAT-ParametersUTRA-TDD-v1020 OPTIONAL,
 nonCriticalExtension UE-EUTRA-Capability-v1060-IEs OPTIONAL 
ETSI
3GPP TS 36.331 version 11.17.0 Release 11 368 ETSI TS 136 331 V11.17.0 (2017-02)
}
UE-EUTRA-Capability-v1060-IEs ::= SEQUENCE {
 fdd-Add-UE-EUTRA-Capabilities-v1060 UE-EUTRA-CapabilityAddXDD-Mode-v1060 OPTIONAL,
 tdd-Add-UE-EUTRA-Capabilities-v1060 UE-EUTRA-CapabilityAddXDD-Mode-v1060 OPTIONAL,
 rf-Parameters-v1060 RF-Parameters-v1060 OPTIONAL,
 nonCriticalExtension UE-EUTRA-Capability-v1090-IEs OPTIONAL
}
UE-EUTRA-Capability-v1090-IEs ::= SEQUENCE {
 rf-Parameters-v1090 RF-Parameters-v1090 OPTIONAL,
 nonCriticalExtension UE-EUTRA-Capability-v1130-IEs OPTIONAL
}
UE-EUTRA-Capability-v1130-IEs ::= SEQUENCE {
 pdcp-Parameters-v1130 PDCP-Parameters-v1130,
 phyLayerParameters-v1130 PhyLayerParameters-v1130 OPTIONAL,
 rf-Parameters-v1130 RF-Parameters-v1130,
 measParameters-v1130 MeasParameters-v1130,
 interRAT-ParametersCDMA2000-v1130 IRAT-ParametersCDMA2000-v1130,
 otherParameters-r11 Other-Parameters-r11,
 fdd-Add-UE-EUTRA-Capabilities-v1130 UE-EUTRA-CapabilityAddXDD-Mode-v1130 OPTIONAL,
 tdd-Add-UE-EUTRA-Capabilities-v1130 UE-EUTRA-CapabilityAddXDD-Mode-v1130 OPTIONAL,
 nonCriticalExtension UE-EUTRA-Capability-v1170-IEs OPTIONAL
}
UE-EUTRA-Capability-v1170-IEs ::= SEQUENCE {
 phyLayerParameters-v1170 PhyLayerParameters-v1170 OPTIONAL,
 ue-Category-v1170 INTEGER (9..10) OPTIONAL,
 nonCriticalExtension UE-EUTRA-Capability-v1180-IEs OPTIONAL
}
UE-EUTRA-Capability-v1180-IEs ::= SEQUENCE {
 rf-Parameters-v1180 RF-Parameters-v1180 OPTIONAL,
 mbms-Parameters-r11 MBMS-Parameters-r11 OPTIONAL, 
ETSI
3GPP TS 36.331 version 11.17.0 Release 11 369 ETSI TS 136 331 V11.17.0 (2017-02)
 fdd-Add-UE-EUTRA-Capabilities-v1180 UE-EUTRA-CapabilityAddXDD-Mode-v1180 OPTIONAL,
 tdd-Add-UE-EUTRA-Capabilities-v1180 UE-EUTRA-CapabilityAddXDD-Mode-v1180 OPTIONAL,
 nonCriticalExtension UE-EUTRA-Capability-v11a0-IEs OPTIONAL
}
UE-EUTRA-Capability-v11a0-IEs ::= SEQUENCE {
 ue-Category-v11a0 INTEGER (11..12) OPTIONAL,
 measParameters-v11a0 MeasParameters-v11a0 OPTIONAL,
 nonCriticalExtension SEQUENCE {} OPTIONAL
}
UE-EUTRA-CapabilityAddXDD-Mode-r9 ::= SEQUENCE {
 phyLayerParameters-r9 PhyLayerParameters OPTIONAL,
 featureGroupIndicators-r9 BIT STRING (SIZE (32)) OPTIONAL,
 featureGroupIndRel9Add-r9 BIT STRING (SIZE (32)) OPTIONAL,
 interRAT-ParametersGERAN-r9 IRAT-ParametersGERAN OPTIONAL,
 interRAT-ParametersUTRA-r9 IRAT-ParametersUTRA-v920 OPTIONAL,
 interRAT-ParametersCDMA2000-r9 IRAT-ParametersCDMA2000-1XRTT-v920 OPTIONAL,
 neighCellSI-AcquisitionParameters-r9 NeighCellSI-AcquisitionParameters-r9 OPTIONAL,
 ...
}
UE-EUTRA-CapabilityAddXDD-Mode-v1060 ::= SEQUENCE {
 phyLayerParameters-v1060 PhyLayerParameters-v1020 OPTIONAL,
 featureGroupIndRel10-v1060 BIT STRING (SIZE (32)) OPTIONAL,
 interRAT-ParametersCDMA2000-v1060 IRAT-ParametersCDMA2000-1XRTT-v1020 OPTIONAL,
 interRAT-ParametersUTRA-TDD-v1060 IRAT-ParametersUTRA-TDD-v1020 OPTIONAL,
 ...,
 [[ otdoa-PositioningCapabilities-r10 OTDOA-PositioningCapabilities-r10 OPTIONAL
 ]]
}
UE-EUTRA-CapabilityAddXDD-Mode-v1130 ::= SEQUENCE {
 phyLayerParameters-v1130 PhyLayerParameters-v1130 OPTIONAL, 
ETSI
3GPP TS 36.331 version 11.17.0 Release 11 370 ETSI TS 136 331 V11.17.0 (2017-02)
 measParameters-v1130 MeasParameters-v1130 OPTIONAL,
 otherParameters-r11 Other-Parameters-r11 OPTIONAL,
 ...
}
UE-EUTRA-CapabilityAddXDD-Mode-v1180 ::= SEQUENCE {
 mbms-Parameters-r11 MBMS-Parameters-r11
}
AccessStratumRelease ::= ENUMERATED {
 rel8, rel9, rel10, rel11, spare4, spare3,
 spare2, spare1, ...}
PDCP-Parameters ::= SEQUENCE {
 supportedROHC-Profiles SEQUENCE {
 profile0x0001 BOOLEAN,
 profile0x0002 BOOLEAN,
 profile0x0003 BOOLEAN,
 profile0x0004 BOOLEAN,
 profile0x0006 BOOLEAN,
 profile0x0101 BOOLEAN,
 profile0x0102 BOOLEAN,
 profile0x0103 BOOLEAN,
 profile0x0104 BOOLEAN
 },
 maxNumberROHC-ContextSessions ENUMERATED {
 cs2, cs4, cs8, cs12, cs16, cs24, cs32,
 cs48, cs64, cs128, cs256, cs512, cs1024,
 cs16384, spare2, spare1} DEFAULT cs16,
 ...
}
PDCP-Parameters-v1130 ::= SEQUENCE {
 pdcp-SN-Extension-r11 ENUMERATED {supported} OPTIONAL,
 supportRohcContextContinue-r11 ENUMERATED {supported} OPTIONAL 
ETSI
3GPP TS 36.331 version 11.17.0 Release 11 371 ETSI TS 136 331 V11.17.0 (2017-02)
}
PhyLayerParameters ::= SEQUENCE {
 ue-TxAntennaSelectionSupported BOOLEAN,
 ue-SpecificRefSigsSupported BOOLEAN
}
PhyLayerParameters-v920 ::= SEQUENCE {
 enhancedDualLayerFDD-r9 ENUMERATED {supported} OPTIONAL,
 enhancedDualLayerTDD-r9 ENUMERATED {supported} OPTIONAL
}
PhyLayerParameters-v9d0 ::= SEQUENCE {
 tm5-FDD-r9 ENUMERATED {supported} OPTIONAL,
 tm5-TDD-r9 ENUMERATED {supported} OPTIONAL
}
PhyLayerParameters-v1020 ::= SEQUENCE {
 twoAntennaPortsForPUCCH-r10 ENUMERATED {supported} OPTIONAL,
 tm9-With-8Tx-FDD-r10 ENUMERATED {supported} OPTIONAL,
 pmi-Disabling-r10 ENUMERATED {supported} OPTIONAL,
 crossCarrierScheduling-r10 ENUMERATED {supported} OPTIONAL,
 simultaneousPUCCH-PUSCH-r10 ENUMERATED {supported} OPTIONAL,
 multiClusterPUSCH-WithinCC-r10 ENUMERATED {supported} OPTIONAL,
 nonContiguousUL-RA-WithinCC-List-r10 NonContiguousUL-RA-WithinCC-List-r10 OPTIONAL
}
PhyLayerParameters-v1130 ::= SEQUENCE {
 crs-InterfHandl-r11 ENUMERATED {supported} OPTIONAL,
 ePDCCH-r11 ENUMERATED {supported} OPTIONAL,
 multiACK-CSI-Reporting-r11 ENUMERATED {supported} OPTIONAL,
 ss-CCH-InterfHandl-r11 ENUMERATED {supported} OPTIONAL,
 tdd-SpecialSubframe-r11 ENUMERATED {supported} OPTIONAL,
 txDiv-PUCCH1b-ChSelect-r11 ENUMERATED {supported} OPTIONAL,
 ul-CoMP-r11 ENUMERATED {supported} OPTIONAL 
ETSI
3GPP TS 36.331 version 11.17.0 Release 11 372 ETSI TS 136 331 V11.17.0 (2017-02)
}
PhyLayerParameters-v1170 ::= SEQUENCE {
 interBandTDD-CA-WithDifferentConfig-r11 BIT STRING (SIZE (2)) OPTIONAL
}
NonContiguousUL-RA-WithinCC-List-r10 ::= SEQUENCE (SIZE (1..maxBands)) OF NonContiguousUL-RAWithinCC-r10

NonContiguousUL-RA-WithinCC-r10 ::= SEQUENCE {
 nonContiguousUL-RA-WithinCC-Info-r10 ENUMERATED {supported} OPTIONAL
}
RF-Parameters ::= SEQUENCE {
 supportedBandListEUTRA SupportedBandListEUTRA
}
RF-Parameters-v9e0 ::= SEQUENCE {
 supportedBandListEUTRA-v9e0 SupportedBandListEUTRA-v9e0 OPTIONAL
}
RF-Parameters-v1020 ::= SEQUENCE {
 supportedBandCombination-r10 SupportedBandCombination-r10
}
RF-Parameters-v1060 ::= SEQUENCE {
 supportedBandCombinationExt-r10 SupportedBandCombinationExt-r10
}
RF-Parameters-v1090 ::= SEQUENCE {
 supportedBandCombination-v1090 SupportedBandCombination-v1090 OPTIONAL
}
RF-Parameters-v10f0 ::= SEQUENCE {
 modifiedMPR-Behavior-r10 BIT STRING (SIZE (32)) OPTIONAL 
ETSI
3GPP TS 36.331 version 11.17.0 Release 11 373 ETSI TS 136 331 V11.17.0 (2017-02)
}
RF-Parameters-v10i0 ::= SEQUENCE {
 supportedBandCombination-v10i0 SupportedBandCombination-v10i0 OPTIONAL
}
RF-Parameters-v10j0 ::= SEQUENCE {
 multiNS-Pmax-r10 ENUMERATED {supported} OPTIONAL
}
RF-Parameters-v1130 ::= SEQUENCE {
 supportedBandCombination-v1130 SupportedBandCombination-v1130 OPTIONAL
}
RF-Parameters-v1180 ::= SEQUENCE {
 freqBandRetrieval-r11 ENUMERATED {supported} OPTIONAL,
 requestedBands-r11 SEQUENCE (SIZE (1.. maxBands)) OF FreqBandIndicator-r11
 OPTIONAL,
 supportedBandCombinationAdd-r11 SupportedBandCombinationAdd-r11 OPTIONAL
}
RF-Parameters-v11d0 ::= SEQUENCE {
 supportedBandCombinationAdd-v11d0 SupportedBandCombinationAdd-v11d0 OPTIONAL
}
SupportedBandCombination-r10 ::= SEQUENCE (SIZE (1..maxBandComb-r10)) OF BandCombinationParameters-r10
SupportedBandCombinationExt-r10 ::= SEQUENCE (SIZE (1..maxBandComb-r10)) OF
BandCombinationParametersExt-r10
SupportedBandCombination-v1090 ::= SEQUENCE (SIZE (1..maxBandComb-r10)) OF BandCombinationParametersv1090

SupportedBandCombination-v10i0 ::= SEQUENCE (SIZE (1..maxBandComb-r10)) OF BandCombinationParametersv10i0

ETSI
3GPP TS 36.331 version 11.17.0 Release 11 374 ETSI TS 136 331 V11.17.0 (2017-02)
SupportedBandCombination-v1130 ::= SEQUENCE (SIZE (1..maxBandComb-r10)) OF BandCombinationParametersv1130

SupportedBandCombinationAdd-r11 ::= SEQUENCE (SIZE (1..maxBandComb-r11)) OF
BandCombinationParameters-r11
SupportedBandCombinationAdd-v11d0 ::= SEQUENCE (SIZE (1..maxBandComb-r11)) OF
BandCombinationParameters-v10i0
BandCombinationParameters-r10 ::= SEQUENCE (SIZE (1..maxSimultaneousBands-r10)) OF BandParameters-r10
BandCombinationParametersExt-r10 ::= SEQUENCE {
 supportedBandwidthCombinationSet-r10 SupportedBandwidthCombinationSet-r10 OPTIONAL
}
BandCombinationParameters-v1090 ::= SEQUENCE (SIZE (1..maxSimultaneousBands-r10)) OF BandParametersv1090

BandCombinationParameters-v10i0::= SEQUENCE {
bandParameterList-v10i0 SEQUENCE (SIZE (1..maxSimultaneousBands-r10)) OF
 BandParameters-v10i0 OPTIONAL
}
BandCombinationParameters-v1130 ::= SEQUENCE {
 multipleTimingAdvance-r11 ENUMERATED {supported} OPTIONAL,
 simultaneousRx-Tx-r11 ENUMERATED {supported} OPTIONAL,
 bandParameterList-r11 SEQUENCE (SIZE (1..maxSimultaneousBands-r10)) OF BandParameters-v1130
 OPTIONAL,
 ...
}
BandCombinationParameters-r11 ::= SEQUENCE {
 bandParameterList-r11 SEQUENCE (SIZE (1..maxSimultaneousBands-r10)) OF
 BandParameters-r11,
 supportedBandwidthCombinationSet-r11 SupportedBandwidthCombinationSet-r10 OPTIONAL,
 multipleTimingAdvance-r11 ENUMERATED {supported} OPTIONAL,
 simultaneousRx-Tx-r11 ENUMERATED {supported} OPTIONAL,
 bandInfoEUTRA-r11 BandInfoEUTRA,
 ... 
ETSI
3GPP TS 36.331 version 11.17.0 Release 11 375 ETSI TS 136 331 V11.17.0 (2017-02)
}
SupportedBandwidthCombinationSet-r10 ::= BIT STRING (SIZE (1..maxBandwidthCombSet-r10))
BandParameters-r10 ::= SEQUENCE {
 bandEUTRA-r10 FreqBandIndicator,
 bandParametersUL-r10 BandParametersUL-r10 OPTIONAL,
 bandParametersDL-r10 BandParametersDL-r10 OPTIONAL
}
BandParameters-v1090 ::= SEQUENCE {
 bandEUTRA-v1090 FreqBandIndicator-v9e0 OPTIONAL,
 ...
}
BandParameters-v10i0::= SEQUENCE {
 bandParametersDL-v10i0 SEQUENCE (SIZE (1..maxBandwidthClass-r10)) OF CA-MIMO-ParametersDLv10i0

}
BandParameters-v1130 ::= SEQUENCE {
 supportedCSI-Proc-r11 ENUMERATED {n1, n3, n4}
}
BandParameters-r11 ::= SEQUENCE {
 bandEUTRA-r11 FreqBandIndicator-r11,
 bandParametersUL-r11 BandParametersUL-r10 OPTIONAL,
 bandParametersDL-r11 BandParametersDL-r10 OPTIONAL,
 supportedCSI-Proc-r11 ENUMERATED {n1, n3, n4} OPTIONAL
}
BandParametersUL-r10 ::= SEQUENCE (SIZE (1..maxBandwidthClass-r10)) OF CA-MIMO-ParametersUL-r10
CA-MIMO-ParametersUL-r10 ::= SEQUENCE {
 ca-BandwidthClassUL-r10 CA-BandwidthClass-r10, 
ETSI
3GPP TS 36.331 version 11.17.0 Release 11 376 ETSI TS 136 331 V11.17.0 (2017-02)
 supportedMIMO-CapabilityUL-r10 MIMO-CapabilityUL-r10 OPTIONAL
}
BandParametersDL-r10 ::= SEQUENCE (SIZE (1..maxBandwidthClass-r10)) OF CA-MIMO-ParametersDL-r10
CA-MIMO-ParametersDL-r10 ::= SEQUENCE {
 ca-BandwidthClassDL-r10 CA-BandwidthClass-r10,
 supportedMIMO-CapabilityDL-r10 MIMO-CapabilityDL-r10 OPTIONAL
}
CA-MIMO-ParametersDL-v10i0 ::= SEQUENCE {
 fourLayerTM3-TM4-r10 ENUMERATED {supported} OPTIONAL
}
CA-BandwidthClass-r10 ::= ENUMERATED {a, b, c, d, e, f, ...}
MIMO-CapabilityUL-r10 ::= ENUMERATED {twoLayers, fourLayers}
MIMO-CapabilityDL-r10 ::= ENUMERATED {twoLayers, fourLayers, eightLayers}
SupportedBandListEUTRA ::= SEQUENCE (SIZE (1..maxBands)) OF SupportedBandEUTRA
SupportedBandListEUTRA-v9e0::= SEQUENCE (SIZE (1..maxBands)) OF SupportedBandEUTRA-v9e0
SupportedBandEUTRA ::= SEQUENCE {
 bandEUTRA FreqBandIndicator,
 halfDuplex BOOLEAN
}
SupportedBandEUTRA-v9e0 ::= SEQUENCE {
 bandEUTRA-v9e0 FreqBandIndicator-v9e0 OPTIONAL
}
MeasParameters ::= SEQUENCE {
 bandListEUTRA BandListEUTRA 
ETSI
3GPP TS 36.331 version 11.17.0 Release 11 377 ETSI TS 136 331 V11.17.0 (2017-02)
}
MeasParameters-v1020 ::= SEQUENCE {
 bandCombinationListEUTRA-r10 BandCombinationListEUTRA-r10
}
MeasParameters-v1130 ::= SEQUENCE {
 rsrqMeasWideband-r11 ENUMERATED {supported} OPTIONAL
}
MeasParameters-v11a0 ::= SEQUENCE {
 benefitsFromInterruption-r11 ENUMERATED {true} OPTIONAL
}
BandListEUTRA ::= SEQUENCE (SIZE (1..maxBands)) OF BandInfoEUTRA
BandCombinationListEUTRA-r10 ::= SEQUENCE (SIZE (1..maxBandComb-r10)) OF BandInfoEUTRA
BandInfoEUTRA ::= SEQUENCE {
 interFreqBandList InterFreqBandList,
 interRAT-BandList InterRAT-BandList OPTIONAL
}
InterFreqBandList ::= SEQUENCE (SIZE (1..maxBands)) OF InterFreqBandInfo
InterFreqBandInfo ::= SEQUENCE {
 interFreqNeedForGaps BOOLEAN
}
InterRAT-BandList ::= SEQUENCE (SIZE (1..maxBands)) OF InterRAT-BandInfo
InterRAT-BandInfo ::= SEQUENCE {
 interRAT-NeedForGaps BOOLEAN
} 
ETSI
3GPP TS 36.331 version 11.17.0 Release 11 378 ETSI TS 136 331 V11.17.0 (2017-02)
IRAT-ParametersUTRA-FDD ::= SEQUENCE {
 supportedBandListUTRA-FDD SupportedBandListUTRA-FDD
}
IRAT-ParametersUTRA-v920 ::= SEQUENCE {
 e-RedirectionUTRA-r9 ENUMERATED {supported}
}
IRAT-ParametersUTRA-v9c0 ::= SEQUENCE {
 voiceOverPS-HS-UTRA-FDD-r9 ENUMERATED {supported} OPTIONAL,
 voiceOverPS-HS-UTRA-TDD128-r9 ENUMERATED {supported} OPTIONAL,
 srvcc-FromUTRA-FDD-ToUTRA-FDD-r9 ENUMERATED {supported} OPTIONAL,
 srvcc-FromUTRA-FDD-ToGERAN-r9 ENUMERATED {supported} OPTIONAL,
 srvcc-FromUTRA-TDD128-ToUTRA-TDD128-r9 ENUMERATED {supported} OPTIONAL,
 srvcc-FromUTRA-TDD128-ToGERAN-r9 ENUMERATED {supported} OPTIONAL
}
IRAT-ParametersUTRA-v9h0 ::= SEQUENCE {
 mfbi-UTRA-r9 ENUMERATED {supported}
}
SupportedBandListUTRA-FDD ::= SEQUENCE (SIZE (1..maxBands)) OF SupportedBandUTRA-FDD
SupportedBandUTRA-FDD ::= ENUMERATED {
 bandI, bandII, bandIII, bandIV, bandV, bandVI,
 bandVII, bandVIII, bandIX, bandX, bandXI,
 bandXII, bandXIII, bandXIV, bandXV, bandXVI, ...,
 bandXVII-8a0, bandXVIII-8a0, bandXIX-8a0, bandXX-8a0,
 bandXXI-8a0, bandXXII-8a0, bandXXIII-8a0, bandXXIV-8a0,
 bandXXV-8a0, bandXXVI-8a0, bandXXVII-8a0, bandXXVIII-8a0,
 bandXXIX-8a0, bandXXX-8a0, bandXXXI-8a0, bandXXXII-8a0}
IRAT-ParametersUTRA-TDD128 ::= SEQUENCE {
 supportedBandListUTRA-TDD128 SupportedBandListUTRA-TDD128
} 
ETSI
3GPP TS 36.331 version 11.17.0 Release 11 379 ETSI TS 136 331 V11.17.0 (2017-02)
SupportedBandListUTRA-TDD128 ::= SEQUENCE (SIZE (1..maxBands)) OF SupportedBandUTRA-TDD128
SupportedBandUTRA-TDD128 ::= ENUMERATED {
 a, b, c, d, e, f, g, h, i, j, k, l, m, n,
 o, p, ...}
IRAT-ParametersUTRA-TDD384 ::= SEQUENCE {
 supportedBandListUTRA-TDD384 SupportedBandListUTRA-TDD384
}
SupportedBandListUTRA-TDD384 ::= SEQUENCE (SIZE (1..maxBands)) OF SupportedBandUTRA-TDD384
SupportedBandUTRA-TDD384 ::= ENUMERATED {
 a, b, c, d, e, f, g, h, i, j, k, l, m, n,
 o, p, ...}
IRAT-ParametersUTRA-TDD768 ::= SEQUENCE {
 supportedBandListUTRA-TDD768 SupportedBandListUTRA-TDD768
}
SupportedBandListUTRA-TDD768 ::= SEQUENCE (SIZE (1..maxBands)) OF SupportedBandUTRA-TDD768
SupportedBandUTRA-TDD768 ::= ENUMERATED {
 a, b, c, d, e, f, g, h, i, j, k, l, m, n,
 o, p, ...}
IRAT-ParametersUTRA-TDD-v1020 ::= SEQUENCE {
 e-RedirectionUTRA-TDD-r10 ENUMERATED {supported}
}
IRAT-ParametersGERAN ::= SEQUENCE {
 supportedBandListGERAN SupportedBandListGERAN,
 interRAT-PS-HO-ToGERAN BOOLEAN
} 
ETSI
3GPP TS 36.331 version 11.17.0 Release 11 380 ETSI TS 136 331 V11.17.0 (2017-02)
IRAT-ParametersGERAN-v920 ::= SEQUENCE {
 dtm-r9 ENUMERATED {supported} OPTIONAL,
 e-RedirectionGERAN-r9 ENUMERATED {supported} OPTIONAL
}
SupportedBandListGERAN ::= SEQUENCE (SIZE (1..maxBands)) OF SupportedBandGERAN
SupportedBandGERAN ::= ENUMERATED {
 gsm450, gsm480, gsm710, gsm750, gsm810, gsm850,
 gsm900P, gsm900E, gsm900R, gsm1800, gsm1900,
 spare5, spare4, spare3, spare2, spare1, ...}
IRAT-ParametersCDMA2000-HRPD ::= SEQUENCE {
 supportedBandListHRPD SupportedBandListHRPD,
 tx-ConfigHRPD ENUMERATED {single, dual},
 rx-ConfigHRPD ENUMERATED {single, dual}
}
SupportedBandListHRPD ::= SEQUENCE (SIZE (1..maxCDMA-BandClass)) OF BandclassCDMA2000
IRAT-ParametersCDMA2000-1XRTT ::= SEQUENCE {
 supportedBandList1XRTT SupportedBandList1XRTT,
 tx-Config1XRTT ENUMERATED {single, dual},
 rx-Config1XRTT ENUMERATED {single, dual}
}
IRAT-ParametersCDMA2000-1XRTT-v920 ::= SEQUENCE {
 e-CSFB-1XRTT-r9 ENUMERATED {supported},
 e-CSFB-ConcPS-Mob1XRTT-r9 ENUMERATED {supported} OPTIONAL
}
IRAT-ParametersCDMA2000-1XRTT-v1020 ::= SEQUENCE {
 e-CSFB-dual-1XRTT-r10 ENUMERATED {supported}
} 
ETSI
3GPP TS 36.331 version 11.17.0 Release 11 381 ETSI TS 136 331 V11.17.0 (2017-02)
IRAT-ParametersCDMA2000-v1130 ::= SEQUENCE {
 cdma2000-NW-Sharing-r11 ENUMERATED {supported} OPTIONAL
}
SupportedBandList1XRTT ::= SEQUENCE (SIZE (1..maxCDMA-BandClass)) OF BandclassCDMA2000
CSG-ProximityIndicationParameters-r9 ::= SEQUENCE {
 intraFreqProximityIndication-r9 ENUMERATED {supported} OPTIONAL,
 interFreqProximityIndication-r9 ENUMERATED {supported} OPTIONAL,
 utran-ProximityIndication-r9 ENUMERATED {supported} OPTIONAL
}
NeighCellSI-AcquisitionParameters-r9 ::= SEQUENCE {
 intraFreqSI-AcquisitionForHO-r9 ENUMERATED {supported} OPTIONAL,
 interFreqSI-AcquisitionForHO-r9 ENUMERATED {supported} OPTIONAL,
 utran-SI-AcquisitionForHO-r9 ENUMERATED {supported} OPTIONAL
}
SON-Parameters-r9 ::= SEQUENCE {
 rach-Report-r9 ENUMERATED {supported} OPTIONAL
}
UE-BasedNetwPerfMeasParameters-r10 ::= SEQUENCE {
 loggedMeasurementsIdle-r10 ENUMERATED {supported} OPTIONAL,
 standaloneGNSS-Location-r10 ENUMERATED {supported} OPTIONAL
}
OTDOA-PositioningCapabilities-r10 ::= SEQUENCE {
 otdoa-UE-Assisted-r10 ENUMERATED {supported},
 interFreqRSTD-Measurement-r10 ENUMERATED {supported} OPTIONAL
}
Other-Parameters-r11 ::= SEQUENCE {
 inDeviceCoexInd-r11 ENUMERATED {supported} OPTIONAL, 
ETSI
3GPP TS 36.331 version 11.17.0 Release 11 382 ETSI TS 136 331 V11.17.0 (2017-02)
 powerPrefInd-r11 ENUMERATED {supported} OPTIONAL,
 ue-Rx-TxTimeDiffMeasurements-r11 ENUMERATED {supported} OPTIONAL
}
Other-Parameters-v11d0 ::= SEQUENCE {
 inDeviceCoexInd-UL-CA-r11 ENUMERATED {supported} OPTIONAL
}
MBMS-Parameters-r11 ::= SEQUENCE {
 mbms-SCell-r11 ENUMERATED {supported} OPTIONAL,
 mbms-NonServingCell-r11 ENUMERATED {supported} OPTIONAL
}
UE-TimersAndConstants ::= SEQUENCE {
 t300 ENUMERATED {
 ms100, ms200, ms300, ms400, ms600, ms1000, ms1500,
 ms2000}, 
ETSI
3GPP TS 36.331 version 11.17.0 Release 11 388 ETSI TS 136 331 V11.17.0 (2017-02)
 t301 ENUMERATED {
 ms100, ms200, ms300, ms400, ms600, ms1000, ms1500,
 ms2000},
 t310 ENUMERATED {
 ms0, ms50, ms100, ms200, ms500, ms1000, ms2000},
 n310 ENUMERATED {
 n1, n2, n3, n4, n6, n8, n10, n20},
 t311 ENUMERATED {
 ms1000, ms3000, ms5000, ms10000, ms15000,
 ms20000, ms30000},
 n311 ENUMERATED {
 n1, n2, n3, n4, n5, n6, n8, n10},
 ...
}
MBMS-NotificationConfig-r9 ::= SEQUENCE {
 notificationRepetitionCoeff-r9 ENUMERATED {n2, n4},
 notificationOffset-r9 INTEGER (0..10),
 notificationSF-Index-r9 INTEGER (1..6)
} 
ETSI
3GPP TS 36.331 version 11.17.0 Release 11 389 ETSI TS 136 331 V11.17.0 (2017-02)
MBSFN-AreaInfoList-r9 ::= SEQUENCE (SIZE(1..maxMBSFN-Area)) OF MBSFN-AreaInfo-r9
MBSFN-AreaInfo-r9 ::= SEQUENCE {
 mbsfn-AreaId-r9 INTEGER (0..255),
 non-MBSFNregionLength ENUMERATED {s1, s2},
 notificationIndicator-r9 INTEGER (0..7),
 mcch-Config-r9 SEQUENCE {
 mcch-RepetitionPeriod-r9 ENUMERATED {rf32, rf64, rf128, rf256},
 mcch-Offset-r9 INTEGER (0..10),
 mcch-ModificationPeriod-r9 ENUMERATED {rf512, rf1024},
 sf-AllocInfo-r9 BIT STRING (SIZE(6)),
 signallingMCS-r9 ENUMERATED {n2, n7, n13, n19}
 },
 ...
}
MBSFN-SubframeConfig ::= SEQUENCE {
 radioframeAllocationPeriod ENUMERATED {n1, n2, n4, n8, n16, n32},
 radioframeAllocationOffset INTEGER (0..7),
 subframeAllocation CHOICE {
 oneFrame BIT STRING (SIZE(6)),
 fourFrames BIT STRING (SIZE(24))
 }
}
PMCH-InfoList-r9 ::= SEQUENCE (SIZE (0..maxPMCH-PerMBSFN)) OF PMCH-Info-r9
PMCH-Info-r9 ::= SEQUENCE {
 pmch-Config-r9 PMCH-Config-r9,
 mbms-SessionInfoList-r9 MBMS-SessionInfoList-r9,
 ...
}
MBMS-SessionInfoList-r9 ::= SEQUENCE (SIZE (0..maxSessionPerPMCH)) OF MBMS-SessionInfo-r9
MBMS-SessionInfo-r9 ::= SEQUENCE {
 tmgi-r9 TMGI-r9,
 sessionId-r9 OCTET STRING (SIZE (1)) OPTIONAL, -- Need OR
 logicalChannelIdentity-r9 INTEGER (0..maxSessionPerPMCH-1),
 ... 
ETSI
3GPP TS 36.331 version 11.17.0 Release 11 392 ETSI TS 136 331 V11.17.0 (2017-02)
}
PMCH-Config-r9 ::= SEQUENCE {
 sf-AllocEnd-r9 INTEGER (0..1535),
 dataMCS-r9 INTEGER (0..28),
 mch-SchedulingPeriod-r9 ENUMERATED {
 rf8, rf16, rf32, rf64, rf128, rf256, rf512, rf1024},
 ...
}
TMGI-r9 ::= SEQUENCE {
 plmn-Id-r9 CHOICE {
 plmn-Index-r9 INTEGER (1..maxPLMN-r11),
 explicitValue-r9 PLMN-Identity
 },
 serviceId-r9 OCTET STRING (SIZE (3))
}
maxBandComb-r10 INTEGER ::= 128 -- Maximum number of band combinations.
maxBandComb-r11 INTEGER ::= 256 -- Maximum number of additional band combinations.
maxBands INTEGER ::= 64 -- Maximum number of bands listed in EUTRA UE caps
maxBandwidthClass-r10 INTEGER ::= 16 -- Maximum number of supported CA BW classes per band
maxBandwidthCombSet-r10 INTEGER ::= 32 -- Maximum number of bandwidth combination sets per
 -- supported band combination
maxCDMA-BandClass INTEGER ::= 32 -- Maximum value of the CDMA band classes
maxCellBlack INTEGER ::= 16 -- Maximum number of blacklisted physical cell identity
 -- ranges listed in SIB type 4 and 5
maxCellInfoGERAN-r9 INTEGER ::= 32 -- Maximum number of GERAN cells for which system in-
 -- formation can be provided as redirection assistance
maxCellInfoUTRA-r9 INTEGER ::= 16 -- Maximum number of UTRA cells for which system
 -- information can be provided as redirection 
ETSI
3GPP TS 36.331 version 11.17.0 Release 11 394 ETSI TS 136 331 V11.17.0 (2017-02)
 -- assistance
maxCSI-IM-r11 INTEGER ::= 3 -- Maximum number of CSI-IM configurations
 -- (per carrier frequency)
maxCSI-Proc-r11 INTEGER ::= 4 -- Maximum number of CSI RS processes (per carrier
 -- frequency)
maxCSI-RS-NZP-r11 INTEGER ::= 3 -- Maximum number of CSI RS resource
 -- configurations using non-zero Tx power
 -- (per carrier frequency)
maxCSI-RS-ZP-r11 INTEGER ::= 4 -- Maximum number of CSI RS resource
 -- configurations using zero Tx power(per carrier
 -- frequency)
maxCQI-ProcExt-r11 INTEGER ::= 3 -- Maximum number of additional periodic CQI
 -- configurations (per carrier frequency)
maxFreqUTRA-TDD-r10 INTEGER ::= 6 -- Maximum number of UTRA TDD carrier frequencies for
 -- which system information can be provided as
 -- redirection assistance
maxCellInter INTEGER ::= 16 -- Maximum number of neighbouring inter-frequency
 -- cells listed in SIB type 5
maxCellIntra INTEGER ::= 16 -- Maximum number of neighbouring intra-frequency
 -- cells listed in SIB type 4
maxCellListGERAN INTEGER ::= 3 -- Maximum number of lists of GERAN cells
maxCellMeas INTEGER ::= 32 -- Maximum number of entries in each of the
 -- cell lists in a measurement object
maxCellReport INTEGER ::= 8 -- Maximum number of reported cells
maxCombIDC-r11 INTEGER ::= 128 -- Maximum number of reported UL CA combinations
maxDRB INTEGER ::= 11 -- Maximum number of Data Radio Bearers
maxEARFCN INTEGER ::= 65535 -- Maximum value of EUTRA carrier frequency
maxEARFCN-Plus1 INTEGER ::= 65536 -- Lowest value extended EARFCN range
maxEARFCN2 INTEGER ::= 262143 -- Highest value extended EARFCN range
maxEPDCCH-Set-r11 INTEGER ::= 2 -- Maximum number of EPDCCH sets
maxFBI INTEGER ::= 64 -- Maximum value of fequency band indicator
maxFBI-Plus1 INTEGER ::= 65 -- Lowest value extended FBI range
maxFBI2 INTEGER ::= 256 -- Highest value extended FBI range
maxFreq INTEGER ::= 8 -- Maximum number of carrier frequencies
maxFreqIDC-r11 INTEGER ::= 32 -- Maximum number of carrier frequencies that are 
ETSI
3GPP TS 36.331 version 11.17.0 Release 11 395 ETSI TS 136 331 V11.17.0 (2017-02)
 -- affected by the IDC problems
maxFreqMBMS-r11 INTEGER ::= 5 -- Maximum number of carrier frequencies for which an
 -- MBMS capable UE may indicate an interest
maxGERAN-SI INTEGER ::= 10 -- Maximum number of GERAN SI blocks that can be
 -- provided as part of NACC information
maxGNFG INTEGER ::= 16 -- Maximum number of GERAN neighbour freq groups
maxLogMeasReport-r10 INTEGER ::= 520 -- Maximum number of logged measurement entries
 -- that can be reported by the UE in one message
maxMBSFN-Allocations INTEGER ::= 8 -- Maximum number of MBSFN frame allocations with
 -- different offset
maxMBSFN-Area INTEGER ::= 8
maxMBSFN-Area-1 INTEGER ::= 7
maxMeasId INTEGER ::= 32
maxMultiBands INTEGER ::= 8 -- Maximum number of additional frequency bands
 -- that a cell belongs to
maxNS-Pmax-r10 INTEGER ::= 8 -- Maximum number of NS and P-Max values per band
maxObjectId INTEGER ::= 32
maxPageRec INTEGER ::= 16 --
maxPhysCellIdRange-r9 INTEGER ::= 4 -- Maximum number of physical
cell identity ranges
maxPLMN-r11 INTEGER ::= 6 -- Maximum number of PLMNs
maxPNOffset INTEGER ::= 511 -- Maximum number of CDMA2000 PNOffsets
maxPMCH-PerMBSFN INTEGER ::= 15
maxRAT-Capabilities INTEGER ::= 8 -- Maximum number of interworking RATs (incl EUTRA)
maxRE-MapQCL-r11 INTEGER ::= 4 -- Maximum number of PDSCH RE Mapping configurations
 -- (per carrier frequency)
maxReportConfigId INTEGER ::= 32
maxRSTD-Freq-r10 INTEGER ::= 3 -- Maximum number of frequency layers for RSTD
 -- measurement
maxSAI-MBMS-r11 INTEGER ::= 64 -- Maximum number of MBMS service area identities
 -- broadcast per carrier frequency
maxSCell-r10 INTEGER ::= 4 -- Maximum number of SCells
maxSTAG-r11 INTEGER ::= 3 -- Maximum number of STAGs
maxServCell-r10 INTEGER ::= 5 -- Maximum number of Serving cells
maxServiceCount INTEGER ::= 16 -- Maximum number of MBMS services that can be included 
ETSI
3GPP TS 36.331 version 11.17.0 Release 11 396 ETSI TS 136 331 V11.17.0 (2017-02)
 -- in an MBMS counting request and response
maxServiceCount-1 INTEGER ::= 15
maxSessionPerPMCH INTEGER ::= 29
maxSessionPerPMCH-1 INTEGER ::= 28
maxSIB INTEGER ::= 32 -- Maximum number of SIBs
maxSIB-1 INTEGER ::= 31
maxSI-Message INTEGER ::= 32 -- Maximum number of SI messages
maxSimultaneousBands-r10 INTEGER ::= 64 -- Maximum number of simultaneously aggregated bands
maxSubframePatternIDC-r11 INTEGER ::= 8 -- Maximum number of subframe reservation patterns
 -- that the UE can simultaneously recommend to the
 -- E-UTRAN for use.
maxUTRA-FDD-Carrier INTEGER ::= 16 -- Maximum number of UTRA FDD carrier frequencies
maxUTRA-TDD-Carrier INTEGER ::= 16 -- Maximum number of UTRA TDD carrier frequencies
END
ETSI
3GPP TS 36.331 version 11.17.0 Release 11 397 ETSI TS 136 331 V11.17.0 (2017-02)
EUTRA-UE-Variables DEFINITIONS AUTOMATIC TAGS ::=
BEGIN
IMPORTS
 AbsoluteTimeInfo-r10,
 AreaConfiguration-r10,
 AreaConfiguration-v1130,
 CarrierFreqGERAN,
 CellIdentity,
 ConnEstFailReport-r11,
 SpeedStateScaleFactors,
 C-RNTI,
 LoggingDuration-r10,
 LoggingInterval-r10,
 LogMeasInfo-r10,
 MeasId,
 MeasIdToAddModList,
 MeasObjectToAddModList,
 MeasObjectToAddModList-v9e0,
 MobilityStateParameters,
 NeighCellConfig,
 PhysCellId,
 PhysCellIdCDMA2000,
 PhysCellIdGERAN,
 PhysCellIdUTRA-FDD,
 PhysCellIdUTRA-TDD,
 PLMN-Identity,
 PLMN-IdentityList3-r11,
 QuantityConfig,
 ReportConfigToAddModList,
 RLF-Report-r9,
 RSRP-Range,
 TraceReference-r10,
 maxCellMeas, 
ETSI
3GPP TS 36.331 version 11.17.0 Release 11 398 ETSI TS 136 331 V11.17.0 (2017-02)
 maxMeasId
FROM EUTRA-RRC-Definitions;
VarConnEstFailReport-r11 ::= SEQUENCE {
 connEstFailReport-r11 ConnEstFailReport-r11,
 plmn-Identity-r11 PLMN-Identity
}
VarLogMeasConfig-r10 ::= SEQUENCE {
 areaConfiguration-r10 AreaConfiguration-r10 OPTIONAL,
 loggingDuration-r10 LoggingDuration-r10,
 loggingInterval-r10 LoggingInterval-r10
}
VarLogMeasConfig-r11 ::= SEQUENCE {
 areaConfiguration-r10 AreaConfiguration-r10 OPTIONAL,
 areaConfiguration-v1130 AreaConfiguration-v1130 OPTIONAL,
 loggingDuration-r10 LoggingDuration-r10, 
ETSI
3GPP TS 36.331 version 11.17.0 Release 11 399 ETSI TS 136 331 V11.17.0 (2017-02)
 loggingInterval-r10 LoggingInterval-r10
}
VarLogMeasReport-r10 ::= SEQUENCE {
 traceReference-r10 TraceReference-r10,
 traceRecordingSessionRef-r10 OCTET STRING (SIZE (2)),
 tce-Id-r10 OCTET STRING (SIZE (1)),
 plmn-Identity-r10 PLMN-Identity,
 absoluteTimeInfo-r10 AbsoluteTimeInfo-r10,
 logMeasInfoList-r10 LogMeasInfoList2-r10
}
VarLogMeasReport-r11 ::= SEQUENCE {
 traceReference-r10 TraceReference-r10,
 traceRecordingSessionRef-r10 OCTET STRING (SIZE (2)),
 tce-Id-r10 OCTET STRING (SIZE (1)),
 plmn-IdentityList-r11 PLMN-IdentityList3-r11,
 absoluteTimeInfo-r10 AbsoluteTimeInfo-r10,
 logMeasInfoList-r10 LogMeasInfoList2-r10
}
LogMeasInfoList2-r10 ::= SEQUENCE (SIZE (1..maxLogMeas-r10)) OF LogMeasInfo-r10
VarMeasConfig ::= SEQUENCE {
 -- Measurement identities
 measIdList MeasIdToAddModList OPTIONAL,
 -- Measurement objects
 measObjectList MeasObjectToAddModList OPTIONAL,
 measObjectList-v9i0 MeasObjectToAddModList-v9e0 OPTIONAL,
 -- Reporting configurations
 reportConfigList ReportConfigToAddModList OPTIONAL,
 -- Other parameters
 quantityConfig QuantityConfig OPTIONAL,
 s-Measure INTEGER (-140..-44) OPTIONAL,
 speedStatePars CHOICE {
 release NULL,
 setup SEQUENCE {
 mobilityStateParameters MobilityStateParameters,
 timeToTrigger-SF SpeedStateScaleFactors
 }
 } OPTIONAL,
 allowInterruptions-r11 BOOLEAN OPTIONAL
}
VarMeasReportList ::= SEQUENCE (SIZE (1..maxMeasId)) OF VarMeasReport
VarMeasReport ::= SEQUENCE {
 -- List of measurement that have been triggered
 measId MeasId,
 cellsTriggeredList CellsTriggeredList OPTIONAL,
 numberOfReportsSent INTEGER
}
CellsTriggeredList ::= SEQUENCE (SIZE (1..maxCellMeas)) OF CHOICE {
 physCellIdEUTRA PhysCellId,
 physCellIdUTRA CHOICE {
 fdd PhysCellIdUTRA-FDD,
 tdd PhysCellIdUTRA-TDD
 },
 physCellIdGERAN SEQUENCE {
 carrierFreq CarrierFreqGERAN,
 physCellId PhysCellIdGERAN
 },
 physCellIdCDMA2000 PhysCellIdCDMA2000
}
ETSI
3GPP TS 36.331 version 11.17.0 Release 11 402 ETSI TS 136 331 V11.17.0 (2017-02)
VarRLF-Report-r10 ::= SEQUENCE {
 rlf-Report-r10 RLF-Report-r9,
 plmn-Identity-r10 PLMN-Identity
}
VarRLF-Report-r11 ::= SEQUENCE {
 rlf-Report-r10 RLF-Report-r9,
 plmn-IdentityList-r11 PLMN-IdentityList3-r11
}
VarShortMAC-Input ::= SEQUENCE {
 cellIdentity CellIdentity,
 physCellId PhysCellId,
 c-RNTI C-RNTI
}
maxLogMeas-r10 INTEGER ::= 4060-- Maximum number of logged measurement entries 
ETSI
3GPP TS 36.331 version 11.17.0 Release 11 403 ETSI TS 136 331 V11.17.0 (2017-02)
 -- that can be stored by the UE
END
EUTRA-InterNodeDefinitions DEFINITIONS AUTOMATIC TAGS ::=
BEGIN
IMPORTS
 AntennaInfoCommon,
 AntennaInfoDedicated-v10i0,
 ARFCN-ValueEUTRA,
 ARFCN-ValueEUTRA-v9e0,
 CellIdentity,
 C-RNTI,
 DL-DCCH-Message,
 InDeviceCoexIndication-r11,
 MasterInformationBlock,
 maxFreq,
 MBMSInterestIndication-r11,
 MeasConfig,
 OtherConfig-r9, 
ETSI
3GPP TS 36.331 version 11.17.0 Release 11 412 ETSI TS 136 331 V11.17.0 (2017-02)
 PhysCellId,
 RadioResourceConfigDedicated,
 RSRP-Range,
 RSRQ-Range,
 SCellToAddModList-r10,
 SecurityAlgorithmConfig,
 ShortMAC-I,
 SystemInformationBlockType1,
 SystemInformationBlockType1-v890-IEs,
 SystemInformationBlockType2,
 UEAssistanceInformation-r11,
 UECapabilityInformation,
 UE-CapabilityRAT-ContainerList
FROM EUTRA-RRC-Definitions;
HandoverCommand ::= SEQUENCE {
 criticalExtensions CHOICE {
 c1 CHOICE{
 handoverCommand-r8 HandoverCommand-r8-IEs,
 spare7 NULL,
 spare6 NULL, spare5 NULL, spare4 NULL,
 spare3 NULL, spare2 NULL, spare1 NULL
 },
 criticalExtensionsFuture SEQUENCE {}
 } 
ETSI
3GPP TS 36.331 version 11.17.0 Release 11 413 ETSI TS 136 331 V11.17.0 (2017-02)
}
HandoverCommand-r8-IEs ::= SEQUENCE {
 handoverCommandMessage OCTET STRING (CONTAINING DL-DCCH-Message),
 nonCriticalExtension SEQUENCE {} OPTIONAL
}
HandoverPreparationInformation ::= SEQUENCE {
 criticalExtensions CHOICE {
 c1 CHOICE{
 handoverPreparationInformation-r8 HandoverPreparationInformation-r8-IEs,
 spare7 NULL,
 spare6 NULL, spare5 NULL, spare4 NULL,
 spare3 NULL, spare2 NULL, spare1 NULL
 },
 criticalExtensionsFuture SEQUENCE {}
 }
} 
ETSI
3GPP TS 36.331 version 11.17.0 Release 11 414 ETSI TS 136 331 V11.17.0 (2017-02)
HandoverPreparationInformation-r8-IEs ::= SEQUENCE {
 ue-RadioAccessCapabilityInfo UE-CapabilityRAT-ContainerList,
 as-Config AS-Config OPTIONAL, -- Cond HO
 rrm-Config RRM-Config OPTIONAL,
 as-Context AS-Context OPTIONAL, -- Cond HO
 nonCriticalExtension HandoverPreparationInformation-v920-IEs OPTIONAL
}
HandoverPreparationInformation-v920-IEs ::= SEQUENCE {
 ue-ConfigRelease-r9 ENUMERATED {
 rel9, rel10, rel11, spare5, v10j0, v11e0,
 spare2, spare1, ...} OPTIONAL, -- Cond HO2
 nonCriticalExtension HandoverPreparationInformation-v9d0-IEs OPTIONAL
}
HandoverPreparationInformation-v9d0-IEs ::= SEQUENCE {
 lateNonCriticalExtension OCTET STRING(CONTAINING HandoverPreparationInformation-v9j0-IEs)
 OPTIONAL,
 nonCriticalExtension HandoverPreparationInformation-v9e0-IEs OPTIONAL
}
-- Late non-critical extensions:
HandoverPreparationInformation-v9j0-IEs ::= SEQUENCE {
 -- Following field is only for pre REL-10 late non-critical extensions
 lateNonCriticalExtension OCTET STRING OPTIONAL,
 nonCriticalExtension HandoverPreparationInformation-v10j0-IEs OPTIONAL
}
HandoverPreparationInformation-v10j0-IEs ::= SEQUENCE {
 as-Config-v10j0 AS-Config-v10j0 OPTIONAL,
 -- Following field is only for late non-critical extensions from REL-10
 nonCriticalExtension SEQUENCE {} OPTIONAL
}
-- Regular non-critical extensions: 
ETSI
3GPP TS 36.331 version 11.17.0 Release 11 415 ETSI TS 136 331 V11.17.0 (2017-02)
HandoverPreparationInformation-v9e0-IEs ::= SEQUENCE {
 as-Config-v9e0 AS-Config-v9e0 OPTIONAL, -- Cond HO2
 nonCriticalExtension HandoverPreparationInformation-v1130-IEs OPTIONAL
}
HandoverPreparationInformation-v1130-IEs ::= SEQUENCE {
 as-Context-v1130 AS-Context-v1130 OPTIONAL, -- Cond HO2
 nonCriticalExtension SEQUENCE {} OPTIONAL
}
UERadioAccessCapabilityInformation ::= SEQUENCE {
 criticalExtensions CHOICE {
 c1 CHOICE{
 ueRadioAccessCapabilityInformation-r8
 UERadioAccessCapabilityInformation-r8-IEs,
 spare7 NULL,
 spare6 NULL, spare5 NULL, spare4 NULL,
 spare3 NULL, spare2 NULL, spare1 NULL
 },
 criticalExtensionsFuture SEQUENCE {}
 }
}
UERadioAccessCapabilityInformation-r8-IEs ::= SEQUENCE {
 ue-RadioAccessCapabilityInfo OCTET STRING (CONTAINING UECapabilityInformation),
 nonCriticalExtension SEQUENCE {} OPTIONAL
}
AS-Config ::= SEQUENCE {
 sourceMeasConfig MeasConfig,
 sourceRadioResourceConfig RadioResourceConfigDedicated,
 sourceSecurityAlgorithmConfig SecurityAlgorithmConfig,
 sourceUE-Identity C-RNTI,
 sourceMasterInformationBlock MasterInformationBlock,
 sourceSystemInformationBlockType1 SystemInformationBlockType1(WITH COMPONENTS
 {..., nonCriticalExtension ABSENT}),
 sourceSystemInformationBlockType2 SystemInformationBlockType2,
 antennaInfoCommon AntennaInfoCommon,
 sourceDl-CarrierFreq ARFCN-ValueEUTRA,
 ...,
 [[ sourceSystemInformationBlockType1Ext OCTET STRING (CONTAINING
 SystemInformationBlockType1-v890-IEs) OPTIONAL,
 sourceOtherConfig-r9 OtherConfig-r9
 -- sourceOtherConfig-r9 should have been optional. A target eNB compliant with this transfer
 -- syntax should support receiving an AS-Config not including this extension addition group
 -- e.g. from a legacy source eNB
 ]],
 [[ sourceSCellConfigList-r10 SCellToAddModList-r10 OPTIONAL
 ]]
}
AS-Config-v10j0 ::= SEQUENCE {
 antennaInfoDedicatedPCell-v10i0 AntennaInfoDedicated-v10i0 OPTIONAL
}
AS-Config-v9e0 ::= SEQUENCE {
 sourceDl-CarrierFreq-v9e0 ARFCN-ValueEUTRA-v9e0
} 
ETSI
3GPP TS 36.331 version 11.17.0 Release 11 418 ETSI TS 136 331 V11.17.0 (2017-02)
AS-Context ::= SEQUENCE {
 reestablishmentInfo ReestablishmentInfo OPTIONAL -- Cond HO
}
AS-Context-v1130 ::= SEQUENCE {
 idc-Indication-r11 OCTET STRING (CONTAINING
 InDeviceCoexIndication-r11) OPTIONAL, -- Cond HO2
 mbmsInterestIndication-r11 OCTET STRING (CONTAINING
 MBMSInterestIndication-r11) OPTIONAL, -- Cond HO2 
ETSI
3GPP TS 36.331 version 11.17.0 Release 11 419 ETSI TS 136 331 V11.17.0 (2017-02)
 powerPrefIndication-r11 OCTET STRING (CONTAINING
 UEAssistanceInformation-r11) OPTIONAL, -- Cond HO2
 ...
}
ReestablishmentInfo ::= SEQUENCE {
 sourcePhysCellId PhysCellId,
 targetCellShortMAC-I ShortMAC-I,
 additionalReestabInfoList AdditionalReestabInfoList OPTIONAL,
 ...
}
AdditionalReestabInfoList ::= SEQUENCE ( SIZE (1..maxReestabInfo) ) OF AdditionalReestabInfo
AdditionalReestabInfo ::= SEQUENCE{
 cellIdentity CellIdentity,
 key-eNodeB-Star Key-eNodeB-Star,
 shortMAC-I ShortMAC-I
} 
ETSI
3GPP TS 36.331 version 11.17.0 Release 11 420 ETSI TS 136 331 V11.17.0 (2017-02)
Key-eNodeB-Star ::= BIT STRING (SIZE (256))
RRM-Config ::= SEQUENCE {
 ue-InactiveTime ENUMERATED {
 s1, s2, s3, s5, s7, s10, s15, s20,
 s25, s30, s40, s50, min1, min1s20c, min1s40,
 min2, min2s30, min3, min3s30, min4, min5, min6,
 min7, min8, min9, min10, min12, min14, min17, min20,
 min24, min28, min33, min38, min44, min50, hr1,
 hr1min30, hr2, hr2min30, hr3, hr3min30, hr4, hr5, hr6,
 hr8, hr10, hr13, hr16, hr20, day1, day1hr12, day2,
 day2hr12, day3, day4, day5, day7, day10, day14, day19,
 day24, day30, dayMoreThan30} OPTIONAL,
 ...,
 [[ candidateCellInfoList-r10 CandidateCellInfoList-r10 OPTIONAL
 ]]
}
CandidateCellInfoList-r10 ::= SEQUENCE (SIZE (1..maxFreq)) OF CandidateCellInfo-r10 
ETSI
3GPP TS 36.331 version 11.17.0 Release 11 421 ETSI TS 136 331 V11.17.0 (2017-02)
CandidateCellInfo-r10 ::= SEQUENCE {
 -- cellIdentification
 physCellId-r10 PhysCellId,
 dl-CarrierFreq-r10 ARFCN-ValueEUTRA,
 -- available measurement results
 rsrpResult-r10 RSRP-Range OPTIONAL,
 rsrqResult-r10 RSRQ-Range OPTIONAL,
 ...,
 [[ dl-CarrierFreq-v1090 ARFCN-ValueEUTRA-v9e0 OPTIONAL
 ]]
}
maxReestabInfo INTEGER ::= 32 -- Maximum number of KeNB* and shortMAC-I forwarded
 -- at handover for re-establishment preparation
ETSI
3GPP TS 36.331 version 11.17.0 Release 11 422 ETSI TS 136 331 V11.17.0 (2017-02)
END
